(DEFUN C:GENMNU( / os)

  (defun SETERR(s)
    (if (= s "Function cancelled")
        (redraw)
        (princ (strcat "\nError: " s))
    ); of If
    (setq *error* oer seterr nil)
    (princ)
  ); of SETERR
  (setq oer *error* *error* seterr)

  (setvar "cmdecho" 0)
  (command "vslide" "DJDG(GENMNU)")
  (setq os (getvar "osmode"))
  (setvar "osmode" 0)
  (setq a (getpoint "\n Select One: "))
  (setvar "osmode" os)
  (redraw)
  (if (listp a)
    (progn
      (setq b (icondwg a))
      (cond
        ((= b  7) (load (strcat (prefix) "DJDG/SPILE1"))  (princ "SPILE1") (c:SPILE1))
        ((= b  8) (load (strcat (prefix) "DJDG/SPILE2"))  (princ "SPILE2") (c:SPILE2))
        ((= b  9) (load (strcat (prefix) "DJDG/RCD"))     (princ "RCD")    (c:RCD))
        ((= b 10) (load (strcat (prefix) "DJDG/ROUND"))   (princ "ROUND")  (c:ROUND))
        ((= b 11) (load (strcat (prefix) "DJDG/SARW"))    (princ "SARW")   (c:SARW))
        ((= b 12) (load (strcat (prefix) "DJDG/ELM"))     (princ "ELM")    (c:ELM))
        ((= b 13) (load (strcat (prefix) "DJDG/THUN"))    (princ "THUN")   (c:THUN))
        ((= b 14) (load (strcat (prefix) "DJDG/TRI"))     (princ "TRI")    (c:TRI))
        ((= b 15) (load (strcat (prefix) "DJDG/PLMARK"))  (princ "PLMARK") (c:PLMARK))
        ((= b 16) (load (strcat (prefix) "DJDG/SLOP"))    (princ "SLOP")   (c:SLOP))
        ((= b 17) (load (strcat (prefix) "DJDG/GRNDMRK")) (princ "GRNDMRK") (c:GRNDMRK))
        ((= b 18) (load (strcat (prefix) "DJDG/WATERM"))  (princ "WATERM")  (c:WATERM))
        ((= b 19) (load (strcat (prefix) "DJDG/SLOPL"))   (princ "SLOPL")   (c:SLOPL))
        ((= b 20) (load (strcat (prefix) "DJDG/RTEXT"))   (princ "RTEXT")   (c:RTEXT))
        ((= b 21) (load (strcat (prefix) "DJDG/WAVE"))    (princ "WAVE")    (c:WAVE))
        ((= b 22) (load (strcat (prefix) "DJDG/MLEAD"))   (princ "MLEAD")   (c:MLEAD))
        ((= b 23) (load (strcat (prefix) "DJDG/SHOE"))    (princ "SHOE")    (c:SHOE))
        ((= b 24) (load (strcat (prefix) "DJDG/LEAD"))    (princ "LEAD")    (c:LEAD))
        ((= b 25) (load (strcat (prefix) "DJDG/DIRMRK"))  (princ "DIRMRK")  (c:DIRMRK))
        ((= b 26) (load (strcat (prefix) "DJDG/BOR"))     (princ "BOR")     (c:BOR))
        ((= b 27) (load (strcat (prefix) "DJDG/ALL-ULT")) (princ "ALL_ULT") (c:ALL-ULT))
        ((= b 28) (load (strcat (prefix) "DJDG/LSLOP")) (princ "LSLOP") (c:LSLOP))
        ((= b 29) (princ "\nEmpty menu"))
        ((= b 30) (princ "\nEmpty menu"))
        ((= b 31) (princ "\nEmpty menu"))
        ((= b 32) (princ "\nEmpty menu"))
        ((= b 33) (princ "\nEmpty menu"))
        ((= b 34) (princ "\nEmpty menu"))
        ((= b 35) (princ "\nEmpty menu"))
        ((= b 36) (princ "\nEmpty menu"))
      );of cond
    );of progn
    (princ "\n Non select ..........! ")
  );of if
  (setq *error* oer seterr nil)
  (princ)
);defun end

 (defun icondwg( xy / x1 x2 x3 x4 x5 x6 x7 y1 y2 y3 y4 y5 y6 y7)

  (setq os (getvar "osmode"))
  (setvar "osmode" 0)
  (setq x (car xy) y (cadr xy))
  (setq cen (getvar "viewctr"))
  (setq h8 (/ (getvar "viewsize") 8.0)
        w8 (* h8 1.36941))
  (setq cx (car cen) cy (cadr cen))

  (setq x1  (- cx (* w8 3))
        x2  (- cx (* w8 2))
        x3  (- cx (* w8 1))
        x4  cx
        x5  (+ cx (* w8 1))
        x6  (+ cx (* w8 2))
        x7  (+ cx (* w8 3))
        y1  (+ cy (* h8 3))
        y2  (+ cy (* h8 2))
        y3  (+ cy (* h8 1))
        y4  cy
        y5  (- cy (* h8 1))
        y6  (- cy (* h8 2))
        y7  (- cy (* h8 3))
   )

  (cond
    ((and (and (> x x1) (< x x2)) (and (< y y1) (> y y2)))  1)
    ((and (and (> x x2) (< x x3)) (and (< y y1) (> y y2)))  2)
    ((and (and (> x x3) (< x x4)) (and (< y y1) (> y y2)))  3)
    ((and (and (> x x4) (< x x5)) (and (< y y1) (> y y2)))  4)
    ((and (and (> x x5) (< x x6)) (and (< y y1) (> y y2)))  5)
    ((and (and (> x x6) (< x x7)) (and (< y y1) (> y y2)))  6)
    ((and (and (> x x1) (< x x2)) (and (< y y2) (> y y3)))  7)
    ((and (and (> x x2) (< x x3)) (and (< y y2) (> y y3)))  8)
    ((and (and (> x x3) (< x x4)) (and (< y y2) (> y y3)))  9)
    ((and (and (> x x4) (< x x5)) (and (< y y2) (> y y3))) 10)
    ((and (and (> x x5) (< x x6)) (and (< y y2) (> y y3))) 11)
    ((and (and (> x x6) (< x x7)) (and (< y y2) (> y y3))) 12)
    ((and (and (> x x1) (< x x2)) (and (< y y3) (> y y4))) 13)
    ((and (and (> x x2) (< x x3)) (and (< y y3) (> y y4))) 14)
    ((and (and (> x x3) (< x x4)) (and (< y y3) (> y y4))) 15)
    ((and (and (> x x4) (< x x5)) (and (< y y3) (> y y4))) 16)
    ((and (and (> x x5) (< x x6)) (and (< y y3) (> y y4))) 17)
    ((and (and (> x x6) (< x x7)) (and (< y y3) (> y y4))) 18)
    ((and (and (> x x1) (< x x2)) (and (< y y4) (> y y5))) 19)
    ((and (and (> x x2) (< x x3)) (and (< y y4) (> y y5))) 20)
    ((and (and (> x x3) (< x x4)) (and (< y y4) (> y y5))) 21)
    ((and (and (> x x4) (< x x5)) (and (< y y4) (> y y5))) 22)
    ((and (and (> x x5) (< x x6)) (and (< y y4) (> y y5))) 23)
    ((and (and (> x x6) (< x x7)) (and (< y y4) (> y y5))) 24)
    ((and (and (> x x1) (< x x2)) (and (< y y5) (> y y6))) 25)
    ((and (and (> x x2) (< x x3)) (and (< y y5) (> y y6))) 26)
    ((and (and (> x x3) (< x x4)) (and (< y y5) (> y y6))) 27)
    ((and (and (> x x4) (< x x5)) (and (< y y5) (> y y6))) 28)
    ((and (and (> x x5) (< x x6)) (and (< y y5) (> y y6))) 29)
    ((and (and (> x x6) (< x x7)) (and (< y y5) (> y y6))) 30)
    ((and (and (> x x1) (< x x2)) (and (< y y6) (> y y7))) 31)
    ((and (and (> x x2) (< x x3)) (and (< y y6) (> y y7))) 32)
    ((and (and (> x x3) (< x x4)) (and (< y y6) (> y y7))) 33)
    ((and (and (> x x4) (< x x5)) (and (< y y6) (> y y7))) 34)
    ((and (and (> x x5) (< x x6)) (and (< y y6) (> y y7))) 35)
    ((and (and (> x x6) (< x x7)) (and (< y y6) (> y y7))) 36)
  ) ;of cond
) ;of defun
