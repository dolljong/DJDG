;--------------------------------
; Program : ALEAD
;           Arc lead
;           Yi Suk Jong
;           04/03/24
;--------------------------------
(defun c:ALEAD(
	       / ds ip cent cp sang eang r angip endang
	         endpnt angip90 intpnt tang lenarw
	         ip1 cp1 crspnt tang1 mirr
	       )

  (setq ds (getvar "DIMSCALE"))
	
  (setq ip (getpoint "\nPick first point: "))
  (push-os)(cecolor "red")
  (command "arc" ip pause pause )
  (setq cent (entget (entlast)))
  (command "arc" "" pause)
  (pop-os)(popcolor)
  
  (setq cp (cdr (assoc 10 cent)))
  (setq sang (cdr (assoc 50 cent)))
  (setq eang (cdr (assoc 51 cent)))
  (setq r (cdr (assoc 40 cent)))
  (setq angip (angle cp ip))
  (if (<= (abs (- angip sang)) (abs (- angip eang)))
    (setq endang eang)
    (setq endang sang)
  );if
  
  (setq endpnt (polar cp endang r))
  (setq angip90 (+ angip (* pi 0.5)))
  (setq intpnt (inters ip cp endpnt (polar endpnt angip90 100) nil))
  (setq tang (angle intpnt endpnt))
  (setq lenarw (* ds 2.8978))
  (setq ip1 (polar ip tang lenarw))
  (setq cp1 (polar cp tang lenarw))
  (setq crspnt (cross cent ip1 cp1))
  (setq tang1 (angle ip crspnt))
  (if (> (dang tang (angle ip endpnt)) 0) (setq mirr -1) (setq mirr 1))
  (push-os)
  (command "insert" (strcat (prefix) "blocks/arw1") ip ds  (* ds mirr) (rtod tang1))
  (pop-os)
  (princ "OK")
  
);defun

;****************************************    
; Function : CROSS    
;            CROSS point of arc & line    
;            By Suk-Jong Yi    
;            1995/6/26    
;****************************************    
;함쩠: 호와 직선의 쏩췽초 찾기    
;     인쩠: ARC entity list, 직선의 첫초 , 직선의 씨초    
;     써과: 직선과 ARC의 쏩췽초    
    
(defun CROSS(aent sp ep /    
aent    sp      ep      a       b       r       sa      ea      x1      x2    
y1      y2      c       d       a1      b1      c1      x1      x2      y1    
y2      ang1    ang2    
)    
    
(push-env)    
(setq a (car (cdr (assoc 10 aent))))      ; ARC entity의 중쫠초 x좌킨    
(setq b (cadr (cdr (assoc 10 aent))))     ; ARC entity의 중쫠초 y좌킨    
(setq r (cdr (assoc 40 aent)))            ; ARC entity의 반지쟎    
(setq sa (cdr (assoc 50 aent)))           ; ARC entity의 시작 각옷    
(setq ea (cdr (assoc 51 aent)))           ; ARC entity의 씨 각옷    
    
(setq x1 (car sp))                        ; LINE entity의 시작초 x좌킨    
(setq x2 (car ep))                        ; LINE entity의 씨초 x좌킨    
(setq y1 (cadr sp))                       ; LINE entity의 시작초 y좌킨    
(setq y2 (cadr ep))                       ; LINE entity의 씨초 y좌킨    
(if (= (- x1 x2) 0)    
  (progn                                    ;x가 constant일 때    
    (setq c x1    
          a1 1                              ;y찌 얾한 2췽방정식의 a    
          b1 (* -2 b)                       ;y찌 얾한 2췽방정식의 b    
          c1 (+ (* c c) (* -2 a c) (* a a) (* b b) (* -1 r r)) ;y찌 얾한 2췽방정식의 c    
          y1 (/ (+ (* -1 b1) (sqrt (- (* b1 b1) (* 4 a1 c1)))) (* 2 a1))  ;근 1    
          y2 (/ (- (* -1 b1) (sqrt (- (* b1 b1) (* 4 a1 c1)))) (* 2 a1))  ;근 2    
    );setq    
  );progn    
  (progn                                    ; y가 x의 함쩠일 때    
    
    (setq c (/ (- y1 y2) (- x1 x2)))          ; y=cx+d찌서 c    
    (setq d (- y2 (* c x2)))                  ; y=cx+d찌서 d    
    (setq a1 (+ 1 (* c c)))                   ; x찌 얾한 이췽방정식의 a    
    (setq b1 (+ (* 2 d c) (* -2 a) (* -2 b c)))   ;x찌 얾한 이췽방정식의 b    
    (setq c1 (+ (* a a) (* b b) (* d d) (* -2 b d) (* -1 r r)))  ;이췽 방정식의 c    
    (setq x1 (/ (+ (* -1 b1) (sqrt (- (* b1 b1) (* 4 a1 c1)))) (* 2 a1)))  ;근 1    
    (setq x2 (/ (- (* -1 b1) (sqrt (- (* b1 b1) (* 4 a1 c1)))) (* 2 a1)))  ;근 2    
    (setq y1 (+ (* c x1) d))                  ;근 1일 때 y값    
    (setq y2 (+ (* c x2) d))                  ;근 2일 때 y값    
  );progn    
)
(setq ang1 (angle (list a b 0.0) (list x1 y1 0.0)))   ;쏩초1의 절얾각(원초찌서)    
(setq ang2 (angle (list a b 0.0) (list x2 y2 0.0)))   ;쏩초2의 절얾각(원초찌서)

;(command "line" sp ep "")  
;(command "line" (list a b 0.0) (list x1 y1 0.0) "")
;(command "line" (list a b 0.0) (list x2 y2 0.0) "")  
  
    
(if (inang sa ea ang1)    
  (list x1 y1 0.0)         ;쏩초1이 호의 시작각과 씨각 사이찌 있으절 쏩초 옻려줌    
  (if (inang sa ea ang2)   ;쏩초2가 호의 시작각과 씨각 사이찌 있으절 쏩초 옻려줌    
    (list x2 y2 0.0)    
    nil                    ;쏩초 1과 2가 모두 각 범챦를 벗어날 경우 nil옻려줌    
  ) ;of if    
)
);defun  


;************************************************************    
; Function : INANG    
;            a angle is IN the range of ANGle-1 and angle-2 ?    
;            By Suk-Jong Yi    
;            1995/6/26    
;*************************************************************    
    
;어떤 각이 주어진 두각(ang1, ang2) 사이에 있는가?    
; 두각 사이에 있는 경우 두각의 차이를 돌려주고    
; 두각 사이에 없는 경우는 nil을 돌려준다.    
    
(defun inang(a1 a2 a3 /             ;인수 정의    
a1 a2 a3                            ;지역변수 정의    
)    
(if (> a1 a2)
  (progn
    (if (or (<= a3 a2) (>= a3 a1)) (- (+ (* 2.0 pi) a2) ) nil)   ;첫각이 두번째 각보다 크면 +360도    , 4사분면 --> 1사분면
  )
  (progn
    (if (and (>= a3 a1) (<= a3 a2)) (- a2 a1)    ;주어진 각이 두각사이에 있으면    
                                nil)         ; 두각의 차이를 돌려줌    
  );                                            ; 두각 사이에 없으면 nil돌려줌       
);if
);defun
