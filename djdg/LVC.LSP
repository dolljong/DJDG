(defun c:lvc()
(setq fp (getpoint "Pick first point: "))
(setq ent (entsel))
(setq fp1 (polar fp (/ pi 2) 1.0))
(setq entp10 (cdr (assoc 10 (entget (car ent)))))
(setq entp11 (cdr (assoc 11 (entget (car ent)))))
(setq crsp (inters fp fp1 entp10 entp11 nil))
(command "line" fp crsp "")
)
