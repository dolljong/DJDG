;****************************************
;*    trsch
;*              Translation character
;*              By Suk-Jong Yi
;*              99/2/9
;****************************************

(defun C:trsch(
              / llist txtlst txtlst1 umlst chlst)     ;ÁöżŞşŻĽöÁ¤ŔÇ

  (setq umlst (getum))

;  (setq umlst (getum1))
  
  (setq sstxt (ssget "X" '((0 . "TEXT"))))   ;¸đµç text ĹĂ
  
  (setq nss (sslength sstxt))			;ss°ąĽö
  (setq index 0)

  (repeat nss					;text°ąĽö¸¸Ĺ­ ąÝşą
    (setq ent (entget (ssname sstxt index)))	;entityÁ¤ş¸ ĂŕĂâ
    (setq oldass1 (assoc 1 ent))   		;textł»żëĂŕĂâ
    (setq oldtxt (cdr oldass1)
	  newtxt oldtxt)
    (setq i 0)
    (setq num (length umlst))                   ;Ŕ˝ŔÇ °ąĽö
    (repeat num					;text list¸¸Ĺ­ ąÝşą
      (setq ums (nth i umlst)
	    nhanja (1- (length ums)))           ;ÇŃŔÚ °ąĽö
      (setq um (nth 0 ums))                     ;ÇŃ±Ű
      (setq j 1)
      (repeat nhanja                             ;ÇŃŔÚ°łĽö¸¸Ĺ­ ąÝşą
        (setq hanja (nth j ums))                 ;get one ÇŃŔÚ 
        (setq newtxt (str-rep newtxt hanja um)) 
        (setq j (1+ j))
      );repeat
      (setq i (1+ i))
    ); repeat
    (setq newass1 (cons 1 newtxt))	;
    (setq entl1 (subst newass1 oldass1 ent))         ;»ő·Îżî entityÁ¤ş¸ŔŰĽş
    (entmod entl1)                            ;»ő·Îżî text·Î ľ÷µĄŔĚĆ®
    (setq index (1+ index))			;´ŮŔ˝textżŁĆĽĆĽ·Î
  );repeat
);defun  


;****************************************
;*    function : DELSPC
;*              DELete SPaCe
;*              By Suk-Jong Yi
;*              03/10/30
;****************************************

(defun delspc( txt / txt1 result lstr i ch)
  (setq txt1 txt)
  (setq result "")
  (setq lstr (strlen txt1))
  (setq i 1)
  (repeat lstr
    (setq ch (substr txt1 i 1))
    (if (/= ch " ")
     (setq result (strcat result ch))
    );if		  
    (setq i (1+ i))
  );repeat
  result
);defun


(defun readhan( )
;      (setq fn (getfiled "INPUT DATA" "" "DAT" 0))      ;file nameŔÔ·Â
      (setq fn (getstring "\nEnter file name: "))      ;file nameŔÔ·Â
      (setq opf (open fn "r"))                          ;file open
      (if opf                                           ;fileŔĚ ľř´Â °ćżě
        (progn
           (setq count 1)
           (while (setq ch (read-line opf))             ;ÇŃÁŮŔ» ŔĐ´Â´Ů
              (princ (chr 13))                          ;ŔÔ·ÂÁß ¸ŢĽĽÁö Ăâ·Â
              (princ count)
              (princ " Line Processing...")
              (setq llist (append llist (list ch)))                   ;llistżˇ Ăß°ˇ
              (setq count (1+ count))                                  ;lineąřČŁ Áő°ˇ
           ) ;of while
        ) ;of progn
        (princ "\nFile not found")                          ;fileŔĚ ľř´Â °ćżě
      ) ;of if
      (close opf)                                           ;file close
    
  (setq nline (length llist))   ;ŔÔ·ÂµĄŔĚĹÍ ¶óŔÎ Ľö

  (setq i 0)
  (repeat nline
    
    (setq line (nth i llist))
    (setq lenstr (strlen line))  ;stringŔĚ
    (setq j 0
	  chlst nil)
    (repeat (1- (fix (/ lenstr 2)))
      (setq chlst (append chlst (list (substr line (1+ (* j 2)) 2))))
      (setq j (1+ j))
    );repeat
    (setq umlst (append umlst  (list chlst)))          			;0, 2, 4
    (setq i (1+ i))
  );repeat  
);defun

(defun str-rep (str pat rep)
  (while (vl-string-search pat str)
    (setq str (vl-string-subst rep pat str))
  )
  str
)



(defun getum( )
  '(
( "°ˇ" "ůĽ" "Ęˇ" "Ę˘" "ĘŁ" "Ę¤" "ĘĄ" "Ę¦" "Ę§" "Ę¨" "Ę©" "ĘŞ" "Ę«" "Ę¬" "Ę®" "Ę­" "ĘŻ" "Ę°" "Ę±" "Ę´" "Ęµ" "ĘĽ" "Ę˛" "Ęł" "Ę¶" "Ę·" "Ę¸" "Ęą" "Ęş" "Ę»" "Ę˝" )
( "°˘" "Ęľ" "Đ»" "Ęż" "ĘŔ" "ĘÁ" "ĘÂ" "ĘĹ" "Ě«" "ĘĂ" "ĘÄ" "ĘĆ" "ĘÇ" "Îň" "ĘČ" )
( "°Ł" "ĘÉ" "ĘĘ" "ĘË" "ĘĚ" "ĘÍ" "ĘÎ" "ĘĎ" "ĘŃ" "ĘŐ" "ĘĐ" "ĘÜ" "ĘŇ" "ĘÓ" "ĘÔ" "ĘÖ" "Ę×" "ĘŘ" "ĘŮ" "ĘÚ" "ĘŰ" "ů×" "ĘÝ" "ĘŢ" "Ęß" "ůŮ" "Ęŕ" )
( "°Ą" "Ęá" "Ęâ" "Ęä" "Ęă" "úÎ" "Ęç" "Ęĺ" "Ęć" "Ęč" "Ęé" "Ęę" )
( "°¨" "Ęë" "Ęě" "Ęí" "Ęî" "Ęđ" "Ęő" "Ęű" "Ęď" "Ęń" "Ęň" "Ęó" "Ęô" "ŐŔ" "Ęö" "Ę÷" "Ęř" "Ęů" "Ęú" "Ęü" "Ęý" "Ęţ" )
( "°©" "Ëˇ" "Ë˘" "Ë¤" "ËŁ" "ËĄ" "Ë¦" )
( "°­" "Ë§" "Ë¨" "Ë©" "ËŞ" "Ë«" "Ë¬" "Ë­" "Ë®" "ËŻ" "Íó" "Ë°" "Ë˝" "Ë·" "Ëą" "Ë±" "Ë˛" "Ëş" "Ëł" "Ë´" "Ëµ" "Ë¶" "Ë¸" "Ë»" "ËĽ" "Ëľ" )
( "°ł" "Ëż" "ËŔ" "ËÁ" "ËÂ" "ËĂ" "ËÄ" "ËĹ" "ËĆ" "ËÉ" "Îż" "ËÇ" "ËČ" "ËÎ" "ËĎ" "ËĘ" "ËË" "ËĚ" "ËÍ" "ËĐ" "ËŃ" "ËŇ" )
( "°´" "ËÓ" "ËÔ" )
( "°»" "ËŐ" "ĚÚ" "Ë×" "ËŘ" )
( "°˝" "ËŮ" )
( "°Ĺ" "ËÚ" "ËŰ" "ËÜ" "ËÝ" "ËŢ" "Ëß" "Ëŕ" "Ëâ" "Ëá" "Ëă" "Ëč" "Ëä" "Ëĺ" "Ëć" "Ëç" "ËŮ" "Ëé" "Ëę" )
( "°Ç" "Ëë" "Ëě" "Ëí" "Ëî" "Ëď" "Ëđ" "Ëň" "Ëń" "Ëó" "Ëô" "Ëő" "Ëö" )
( "°É" "Ë÷" "Ëř" "Ëů" "Ëú" )
( "°Ë" "Ëű" "Ëý" "Ëü" "Ëţ" "Ěˇ" "Ě˘" "ĚŁ" )
( "°Ě" "Ě¤" "ĚĄ" "Ě¦" )
( "°Ô" "Ě§" "Ě©" "Ě¨" )
( "°Ý" "ĘŁ" "Ě­" "Ě°" "ĚŞ" "Ě®" "Ě«" "Ě¬" "ĚŻ" )
( "°ß" "Ě±" "Ě·" "Ě˛" "Ěł" "Ěş" "Ě´" "Ěµ" "Ě¶" "Ě¸" "Ěą" "ăó" "Ě»" )
( "°á" "Ěř" "ĚĽ" "Ě˝" "Ěľ" "Ěż" "ĚŔ" "ĚÁ" )
( "°â" "ĚÂ" "ĚĂ" "Ęó" "ĚÄ" "ĚĹ" "ĚĆ" "ĚÇ" )
( "°ć" "ĚČ" "ĚÉ" "ĚĘ" "ĚË" "ĚĚ" "ĚÍ" "ĚÎ" "ĚĎ" "ĚĐ" "ĚŃ" "ĚŇ" "ĚÓ" "ĚŐ" "ĚÜ" "ĚÔ" "ĚÖ" "Ě×" "ĚŘ" "ĚŮ" "ĚÚ" "Ěë" "ĚŰ" "ĚÝ" "ĚŢ" "Ěß" "Ěŕ" "Ěá" "Ěě" "Ěď" "Ěâ" "Ěă" "Ěä" "Ěĺ" "Ěć" "Ěç" "Ěč" "Ěé" "Ěę" "Ěí" "Ěî" "Ěđ" "Ěń" "Ěň" "Ěó" "Ěô" )
( "°č" "Ěő" "Ěö" "Ě÷" "Ěř" "Ěů" "Ěú" "Ěű" "Í˘" "Í­" "Ěü" "Ěý" "Ěţ" "Íˇ" "ÍŁ" "Í¤" "ÍĄ" "Í¦" "Í§" "Ěż" "Í¨" "Í©" "ÍŞ" "Í«" "Í¬" "Í®" )
( "°í" "ÍŻ" "Í°" "Í±" "Í˛" "Íł" "Í´" "Íµ" "Ę«" "Í¶" "Í·" "Í¸" "Íż" "Íą" "Íş" "Í»" "ÍĽ" "ÍĆ" "ÍÇ" "Í˝" "Íľ" "ÍĹ" "ÍÉ" "ÍČ" "ÍĘ" "ÍË" "ÍŔ" "ÍÁ" "ÍÂ" "ÍĂ" "ÍÍ" "ÍÄ" "ÍĚ" "ÍÎ" "Ęą" "ÍĎ" "ÍĐ" "ÍŃ" "ÍŇ" "ÍÓ" "ÍÔ" "ÍŐ" )
( "°î" "Í±" "ÍÖ" "Í×" "ÍŘ" "ÍŮ" "ÍÚ" "ÍŰ" "ÍÜ" )
( "°ď" "ÍÝ" "ÍŢ" "Íß" "Íă" "Íŕ" "Íá" "Íâ" "Íä" "Íĺ" "Íć" )
( "°ń" "Íç" "Íč" "Íé" )
( "°ř" "Íę" "Íë" "Íě" "Íí" "Íî" "Íď" "Íň" "Íó" "Íđ" "Íń" "Íô" "Íő" "Íö" "űő" "Í÷" "Íř" "Íů" )
( "°ů" "Íú" )
( "°ú" "Íű" "Íü" "Íý" "Î˘" "Î¦" "Íţ" "Îˇ" "ÍÍ" "ÎŁ" "Î¤" "ÎĄ" "Î§" "Î¨" )
( "°ű" "Î©" "Î¬" "ÎŞ" "Î«" )
( "°ü" "Íú" "Î®" "ÎŻ" "Î°" "ĘĎ" "Î±" "Î´" "Î˛" "Ďí" "Îł" "Îµ" "Î¶" "Îą" "Đč" "Î·" "Î¸" "Îş" "Î»" "ÎĽ" "Î˝" )
( "°ý" "Îľ" "ÎŔ" "Îż" "ÎÁ" )
( "±¤" "ÎÂ" "ÎĂ" "ÎÄ" "ÎĹ" "ÎĆ" "ÎČ" "ÎĘ" "ÎÇ" "ÎÍ" "ÎÉ" "ÎË" "ÎĚ" "ÎÎ" )
( "±Ą" "ÎĎ" "ÎĐ" "ÎŃ" )
( "±«" "ÎŇ" "ÎÓ" "ÎÔ" "ÎŐ" "ÎÖ" "Î×" "ÎŘ" "üę" "ÎŮ" "ÎÚ" )
( "±˛" "ÎŰ" "ÎÝ" "ÎÜ" "ÎŢ" )
( "±ł" "Îß" "Îŕ" "Îá" "Îâ" "Îă" "Îä" "Îĺ" "ôý" "Îć" "Îę" "Îô" "Îç" "Îď" "Îč" "Îé" "Îđ" "Îë" "Îě" "Đ¬" "Îí" "Îî" "Îń" "ĘĆ" "Îň" "Îó" "áň" "Îő" "Îö" "Î÷" )
( "±¸" "Îř" "Îů" "Îú" "Îű" "Îü" "Îý" "Îţ" "Ďˇ" "Ď˘" "ĎŁ" "Ď¤" "ĎĄ" "Ď¦" "Ď§" "Ď¨" "Ď©" "ĎŞ" "Ď«" "Ď¬" "Ďµ" "Ď·" "ĎČ" "Ď­" "Ď®" "ĎŻ" "Ď°" "Ď±" "Ď˛" "Ďł" "Ď´" "Ď¶" "Ď¸" "Ďą" "Ďľ" "ĎÂ" "ĎÇ" "Ďş" "Ď»" "ĎĽ" "Ď˝" "Ďż" "ĎŔ" "ĎÁ" "ĎĂ" "Ë»" "ĎÄ" "ĎĹ" "ĎĆ" "ĎÉ" "ĎĘ" "ĎË" "ĎĚ" "ĎÍ" "ĎÎ" "Đ˘" )
( "±ą" "Í±" "ĎĐ" "ĎŃ" "ĎŇ" "ĎÓ" "ĎÔ" "ĎŐ" )
( "±ş" "ĎÖ" "ĎŰ" "Ď×" "ĎŮ" "ĎŘ" "ĎÚ" )
( "±Ľ" "ĎÜ" "ĎÝ" "ĎŢ" "Ďß" )
( "±Ă" "Ďŕ" "Ďá" "Ďä" "Ďâ" "Ďă" "Ďĺ" "ĎÓ" )
( "±Ç" "Ďć" "Ďç" "Ďč" "Ďé" "Ďę" "Ďě" "Ďî" "Ďë" "Ďí" "Ďď" )
( "±Č" "Ďđ" "ĎŢ" "Ďń" "Ďň" "Ďó" "Ďô" )
( "±Ë" "Ď÷" "Ďő" "Ďö" "Ďř" "Ďó" "Ďů" "Ďú" )
( "±Í" "ĎŁ" "Ďü" "Ďý" "Ďţ" "Đˇ" "Đ˘" )
( "±Ô" "ĐŁ" "Đ¤" "ĐĄ" "Đ¦" "Đ§" "Đ¨" "Đ­" "Đ°" "Đ©" "ĐŞ" "Đ«" "Đ¬" "Ůđ" "Đ®" "ĐŻ" "Đ±" "Ěń" )
( "±Ő" "Đ˛" "Đł" "Đ¶" "Đ´" "Đµ" "Đ·" "Đ˘" )
( "±Ö" "Đą" )
( "±Ř" "Đş" "Đ»" "ĐĽ" "Ę¦" "ĐŔ" "Đ˝" "Đľ" "Đż" "úÔ" )
( "±Ů" "ĐÁ" "ĐÂ" "ĐĂ" "ĐÄ" "ĐĹ" "ĐĆ" "ĐÇ" "ĐČ" "ĐĘ" "ĐË" "ĐÎ" "Đč" "ĐÉ" "ĐĚ" "ĐÍ" "Ě˘" "ĐĎ" )
( "±Ű" "Ěř" "ýá" )
( "±Ý" "ĐŃ" "ëá" "ĐŇ" "ĐÓ" "ĐÔ" "ĐŐ" "ĐÖ" "ĐŮ" "Đ×" "ĐŘ" "ĐŰ" "ĐÜ" "ĐÚ" "ĐÝ" "ĐŢ" "ĚŁ" )
( "±Ţ" "Đß" "Đŕ" "Đâ" "Đă" "Đá" "Đä" "Đĺ" )
( "±ŕ" "Đć" "Đç" "ůö" "Đé" "Đč" )
( "±â" "Đę" "Đë" "ëď" "Đě" "Đí" "Đî" "Đď" "Đđ" "Đň" "Đń" "Đô" "Đő" "Đö" "ËÜ" "Đ÷" "Đř" "Đů" "Đú" "Đü" "ŃŞ" "Ń©" "Ń«" "ËÉ" "Đű" "Đó" "Đý" "Đţ" "Ń˘" "Ńˇ" "Ńż" "ŃŁ" "ň«" "ŃĄ" "Ń¤" "Ń¦" "Ń§" "Ń¨" "Ń¬" "Ń­" "Ń®" "ŃŻ" "Ń°" "ĐÎ" "Ń±" "Ń˛" "Ńł" "Ń´" "ăĆ" "Ńµ" "Ń¶" "Ń·" "Ń¸" "ŃĽ" "Ńą" "Ńş" "Ń»" "Ń˝" "Ńľ" "ŃŔ" "ŃÁ" "ŃÂ" "ŃĂ" "ŃĹ" "ŃÄ" "ŃĆ" "ŃÇ" "ŃÉ" "ŃČ" "ŃĘ" "ŃË" )
( "±ä" "ŃĚ" )
( "±ć" "ŃÍ" "ŃÎ" "ŃĎ" "ŃĐ" )
( "±č" "ĐÝ" )
( "łŁ" "ŃŇ" )
( "łŞ" "ŃÓ" "í©" "ŃÔ" "ŇŻ" "ŃÖ" "Ń×" "ŃŘ" "Ńá" "ŃŮ" "ŃÚ" "Ň°" "Őˇ" "Ő¤" "Ôý" "Ôţ" "ŐŁ" "Ő˘" )
( "ł«" "Ő¦" "Ńâ" "Ő§" "Ő¨" "ŐŞ" "Ńç" "Ő¬" "Ő­" )
( "ł­" "ŐŻ" "Ő°" "Ńě" "Ő±" "Ńî" "Ő´" "Ńđ" "Ńń" "Ő¶" )
( "łŻ" "Ńó" "Ńô" )
( "ł˛" "Ńő" "Őą" "Ńů" "Ő˝" "Ń÷" "Ńř" "ŐŔ" "Ńű" "ŐÁ" )
( "łł" "Ň®" "ŐĂ" "ŐÄ" "Ň¤" "Ňˇ" "ŐĹ" )
( "ł¶" "ŇĄ" "Ň¦" "ŐĆ" "ŐČ" "ŐÉ" "Ň«" "ŐÇ" )
( "ł»" "Ň¬" "ŐÎ" "Ň®" "ŇŻ" "Ńá" "Ňö" "Ň°" "Ň±" )
( "łĂ" "ŐŇ" )
( "łŕ" "Ňł" )
( "łâ" "Ň´" "Ňµ" "Ň¶" "ď­" )
( "łä" "Ň¸" "Ňą" "Ňş" "Ň·" )
( "łĺ" "ŕî" )
( "łç" "ŇĽ" "Ň»" )
( "łë" "Ň˝" "ÖĚ" "Ňż" "÷¶" "ŇŔ" "ÖĎ" "ŇÁ" "ÖĐ" "ÖÓ" "ŇĹ" "ÖÖ" "ÖÔ" "ÖŐ" "Ö×" "ÖŘ" "ÖÚ" "ŇĚ" "ÖŰ" "ÖÜ" )
( "łě" "Öá" "ÖŢ" "Öß" "Öŕ" "ÍŰ" "Öâ" "Öă" )
( "łí" "Öĺ" )
( "łó" "Öć" "Öç" "ŇŘ" "ŇŰ" "Öë" "Öě" "ŇÜ" )
( "łú" "ŇÝ" "Ňŕ" "Öď" "Öđ" "Öń" "Öô" )
( "´˘" "Ňă" "čő" "Ňü" "čú" )
( "´©" "×¤" "×¦" "×¨" "×©" "×°" "×§" "×«" "×¬" )
( "´«" "Ňě" )
( "´­" "Ňí" )
( "´ş" "Ňî" "Ňď" )
( "´Á" "×Í" "×Î" )
( "´Ć" "×Ď" "ů˘" )
( "´É" "×Đ" "×Ő" "Ňö" "×Ô" "×Ň" "×Ó" )
( "´Ď" "Ňů" "Ňú" )
( "´Đ" "Ňű" "Ňü" )
( "´Ů" "Ňý" "Ňţ" )
( "´Ü" "Óˇ" "Ó˘" "ÓŁ" "Ó¤" "ÓĄ" "Ó¦" "Ó§" "Ó¬" "Ół" "ÔÄ" "Ó¨" "Ó©" "ÓŞ" "Ó«" "Ó­" "Ó®" "Ó˛" "ÓŻ" "Ó°" "Ó±" "Ó´" )
( "´Ţ" "ýÂ" "Óµ" "Ó¶" "Ó·" "Óą" "Ó¸" )
( "´ă" "Óş" "Ó»" "ÓĽ" "Ęđ" "Ó˝" "Óż" "ÓŔ" "ÓÁ" "ÓÂ" "Óľ" "ÓĹ" "ćú" "ÓĆ" "ÓĂ" "ÓÄ" "ÓÇ" "ÓČ" "ÓÉ" "ÓĘ" )
( "´ä" "ÓË" "ÓĎ" "ÓĚ" "ÓÍ" "ÓÎ" )
( "´ç" "ÓĐ" "ÓŃ" "ÓŇ" "ÓÓ" "ÓŐ" "ÓÔ" "ÓÖ" "Ó×" "ÓŘ" "ÓŮ" "ÓÚ" )
( "´ë" "ÓŰ" "÷»" "ÓÜ" "ÓÝ" "ÓŢ" "Óß" "Óŕ" "Óá" "Óâ" "Óä" "Óé" "Óă" "ÔÄ" "Óĺ" "ôö" "Óć" "Óç" "Óč" "î°" "âö" "Óę" )
( "´ě" "÷Č" )
( "´ö" "Ôđ" "Óě" "Óí" )
( "µµ" "Óî" "Óď" "Óđ" "Óń" "Óň" "Óó" "Óô" "Óő" "Óö" "Ó÷" "Óř" "Óů" "Óú" "Óű" "Óü" "Óý" "ÔŁ" "Ô¤" "ÔĄ" "Ô¦" "Ô´" "Ô¶" "ÔÄ" "Óţ" "Ôˇ" "Ô˘" "Ô§" "Ô¬" "Ô±" "Ô˛" "Ôł" "Ô¨" "Ô©" "ÔŞ" "Ô«" "ńĆ" "Ô­" "Ô®" "ÔŻ" "Ô°" "Ôµ" "Ô·" )
( "µ¶" "Ôą" "ÔĽ" "Ô¸" "Ôş" "Ô»" "Ô˝" "Ôľ" "őç" "Ôż" "ÔŔ" "ÔÁ" )
( "µ·" "ÔÂ" "ÔĂ" "ÔÇ" "ÔÄ" "ÔĹ" "ÔĆ" "ÔČ" "ÔÉ" "âę" "âí" "ÔĘ" "ÔË" )
( "µą" "ÔĚ" "ÔÍ" "ÔË" )
( "µż" "ÔÎ" "ÔĎ" "ÔĐ" "ÔŃ" "ÔŇ" "ÔÓ" "Ô×" "ÔŘ" "ÔÜ" "ÔÔ" "ÔŐ" "ÔÖ" "ÔÝ" "ÔŮ" "ÔÚ" "ÔŰ" "ńě" "ÔŢ" )
( "µÎ" "Ôß" "÷Ď" "÷á" "Ôą" "Ôŕ" "Ôá" "Ôâ" "Ôĺ" "Ôč" "Ôă" "Ôä" "ÔÁ" "Ôç" "Ôé" )
( "µĐ" "Ôę" "Ôë" "Ôě" "Ôí" "Ôî" "Ôď" "ÔË" )
( "µć" "Ôđ" )
( "µî" "Ôń" "Ôř" "Ôň" "Ôó" "Ôö" "Ôô" "Ôő" "Ô÷" "Ôů" )
( "¶ó" "Ôú" "Ôű" "ŃÚ" "Őˇ" "Ő¤" "Ôý" "Ôţ" "ŐŁ" "×«" "Ő˘" )
( "¶ô" "Ő¦" "ŐĄ" "Ő§" "Ő¨" "ŐŞ" "Ő©" "Ńç" "ÖŮ" "Ő¬" "Ő­" )
( "¶ő" "Óˇ" "ŐŻ" "Ő°" "Őł" "Ő±" "Ő˛" "Ő´" "Őµ" "Ő¶" )
( "¶ö" "Ő·" "Ő¸" )
( "¶÷" "Őą" "Ő»" "Ő˝" "Őş" "ŐĽ" "ŐŔ" "ŐÁ" "Őľ" "Őż" "ŐÂ" )
( "¶ř" "ŐĂ" "ŐÄ" "ŐĹ" )
( "¶ű" "Ň¦" "ŐĆ" "ŐČ" "ŐÉ" "ŐÍ" "ŐÇ" "ŐĘ" "ŐË" "ŐĚ" )
( "·ˇ" "ŐÎ" "ŐĎ" "ŐĐ" "ŐŃ" "×í" )
( "·©" "ŐŇ" )
( "·«" "ŐÓ" "ŐÔ" )
( "·®" "ŐŐ" "ŐÖ" "Ő×" "ŐŘ" "ŐŮ" "ŐÚ" "ŐÜ" "ŐŰ" "ŐÝ" "ŐŢ" "Őß" "Őŕ" "Őá" )
( "·Á" "Őâ" "Őă" "Őä" "Őĺ" "Őć" "Őë" "Őç" "Őč" "Őé" "Őę" "×ŕ" "Őí" "Őě" "Őî" "Öâ" "Őď" "Őđ" "Őń" "Őň" "Őó" )
( "·Â" "Őô" "Ő÷" "Őő" "Őö" "Őř" "Őů" "Őú" )
( "·Ă" "Őű" "Őţ" "Őü" "Őý" "Öˇ" "Ö˘" "ÖĄ" "Ö§" "ÖŁ" "Ö¤" "Ö¦" "Ö¨" )
( "·Ä" "Ö©" "ÖŞ" "Ö«" "Ö¬" "Ö­" "Ö®" "·Ĺ" "ÖŻ" "Ö˛" "Ö°" "Ö±" "Öł" )
( "·Ć" "Ö´" )
( "·É" "Öµ" "Ö¶" "Ö·" "Ň»" "Öą" "Öş" "Ö»" "ÖĽ" "ÖÁ" "Ö˝" "Öľ" "Öż" "ÖŔ" "ÖÂ" "ÖĂ" "ÖÄ" "ÖĹ" "ÖĆ" )
( "·Ę" "ÖÇ" "Ö©" "ÖČ" "ÖÉ" "ÖĘ" "ÖË" )
( "·Î" "Ň˝" "ÖĚ" "Őć" "ÖÎ" "ÖĎ" "ÖŃ" "ÖŇ" "ÖĐ" "ÖÓ" "ÖÖ" "ÖÔ" "ÖŐ" "Ö×" "ÖŘ" "ÖŮ" "ÖÚ" "ÖŰ" "ÖÜ" "ÖÝ" )
( "·Ď" "Öá" "ÖŢ" "Öß" "Öŕ" "ÍŰ" "Öâ" "Öă" "Öä" )
( "·Đ" "Öĺ" )
( "·Ő" "Öć" "Öç" "Öé" "Öč" "Öę" "Öë" "Öě" "×Ł" "ŰÂ" )
( "·Ú" "Öí" "×¤" "Öî" "Öď" "Öđ" "Öń" "Öň" "Öó" "Öô" "×ľ" )
( "·á" "Öő" "Öö" "čď" "Ö÷" "Öř" "Öů" "Öú" "Öţ" "×ˇ" "Öű" "Öü" "Ůđ" "Öý" "×˘" )
( "·ć" "×Ł" )
( "·ç" "×¤" "×Ą" "×¦" "×¨" "×©" "×°" "×§" "×­" "×Ş" "×®" "×«" "×¬" "×Ż" )
( "·ů" "×±" "×µ" "ęý" "×¶" "×·" "×˛" "×ł" "×´" "×ŕ" "×¸" "×ą" "×ş" "×»" "×Ľ" "×˝" "×ľ" )
( "·ú" "×ż" "×Á" "×Ŕ" )
( "·ű" "×Â" "×Ă" "×Ä" "×Ĺ" "×Ć" "Öĺ" "×Ç" )
( "·ü" "×¤" "×Č" "×É" "×Ę" "×Ë" )
( "¸˘" "×Ě" )
( "¸¤" "×Í" "×Î" )
( "¸§" "×Ď" "ů˘" )
( "¸Ş" "×Đ" "×Ő" "×Ń" "×Ô" "×Ň" "×Ó" )
( "¸®" "×Ö" "××" "×Ř" "×Ů" "×Ú" "×Ű" "×Ü" "×ß" "×á" "×Ý" "×Ţ" "×ŕ" "×â" "×ă" "×é" "ě¶" "×ĺ" "×ç" "×ë" "×ć" "×č" "×ę" "×ě" "×í" "×î" "×ď" )
( "¸°" "×đ" "×ń" "×ö" "×ň" "×ó" "×ô" "×ő" "×÷" "×ř" )
( "¸˛" "×ú" "×ů" "×ű" "×ü" "×ý" )
( "¸ł" "×ţ" "Řˇ" "Ř˘" "ŘŁ" )
( "¸¶" "Ř¤" "ŘĄ" "Ř¦" "Ř§" "Ř¨" "ÚĽ" "Ř©" "ŘŞ" "Ř«" )
( "¸·" "Ř¬" "Ř­" "Ř®" "ŘŻ" "Ř°" "Ř±" "ŮÉ" )
( "¸¸" "Ř˛" "Řł" "Ř´" "Řµ" "Ř¶" "Ř·" "Ř¸" "ŘĽ" "Ř»" "Ř˝" "Řą" "Řş" "Řż" "ŘŔ" "Řľ" "ŘÁ" "Î»" "ŘÂ" "ŘĂ" "ŘÄ" )
( "¸»" "ŘĹ" "ŘĆ" "ŘČ" "ŘÇ" "ŘÉ" "ŘĘ" "ŘË" )
( "¸Á" "ŘĚ" "ŘÍ" "ŘĎ" "Ř×" "ŘÎ" "ŘĐ" "ŘÓ" "ŘÔ" "ŘŐ" "ŘŇ" "ŘŃ" "ŘÖ" "×Ł" )
( "¸Ĺ" "ŘŘ" "ŘŮ" "ŘÚ" "ŘŰ" "ŘÜ" "ŘÝ" "ŘŢ" "Řß" "Řŕ" "ŮÁ" "Řä" "Řá" "Řâ" "Řă" "Řĺ" )
( "¸Ć" "Řč" "Řć" "ŰÝ" "Řç" "Řé" "Řę" )
( "¸Í" "Řë" "Ří" "Řě" "Řđ" "Řď" "Řî" )
( "¸č" "Řń" "Íç" "Řň" )
( "¸é" "Řó" "Řô" "Řő" "Ř÷" "Řö" "Řř" "Řů" "ŮŞ" "Řú" "ÚÉ" "Řű" "Řü" "Řý" )
( "¸ę" "Řţ" "Ůˇ" )
( "¸í" "Ů˘" "ŮŁ" "Ů¤" "Ů¨" "ŮĄ" "Ů¦" "Ů§" "Ů«" "Ů¬" "Ů©" "ŮŞ" "Ů­" "Ů®" "ŮŻ" "Ů°" )
( "¸ď" "Ů±" )
( "¸đ" "Ů˛" "Ůł" "Ůâ" "Ů´" "Ůµ" "Ů¶" "Ů¸" "Ů·" "Ůą" "Ůş" "ŘŻ" "Ů»" "ŮĽ" "Ůě" "Ů˝" "Ůľ" "Ůż" "ŮŔ" "ŮÁ" "ŮĹ" "ŮĆ" "Ř°" "ŮÂ" "ŮĂ" "ŮÄ" "ŮÇ" "ŮČ" "ŮÉ" )
( "¸ń" "Ůâ" "ůŻ" "ŮË" "Ř÷" "ŮĘ" "ŮĚ" "ŮÍ" "ŮÎ" "ŮĎ" "Ůđ" "ŮĐ" )
( "¸ô" "Ú¨" "ŮŇ" "ŮŃ" )
( "¸ů" "ŮÓ" "ŮÔ" "ŮŐ" )
( "ą¦" "ŮÖ" "Ů×" "ŮŘ" "ŮŮ" "ŮÚ" "ŮÝ" "ŮŢ" "ŮŰ" "ŮÜ" "Ůŕ" "Ůď" "Ůß" "Ůá" )
( "ą«" "ŘĚ" "Ůâ" "Ůµ" "Ůă" "Ůä" "Ůç" "Ůč" "Ůĺ" "Ůć" "Ůé" "Ůę" "Ůë" "Ůě" "Ůí" "Ůî" "Ůň" "Ůó" "Ůď" "Ůđ" "Ůń" "Ůô" "Ůő" "Ůö" "Ů÷" )
( "ą¬" "Ůł" "Ůř" "Ůů" )
( "ą®" "Ůú" "Řó" "Ůű" "Ůü" "Ůý" "Ř´" "Úˇ" "Ůţ" "ëÉ" "Řľ" "ÚŁ" "Ú˘" "Ú¤" "ÚĄ" "Ú¦" "Ú§" )
( "ą°" "Ú¨" "Ú©" "ÚŞ" )
( "ąĚ" "Ú«" "Ú¬" "Ú­" "Ú®" "ÚŻ" "Ú°" "Ú´" "Úµ" "Ú±" "Ú˛" "Úł" "Úą" "Ú»" "Ú¶" "Ú·" "Ú¸" "Úş" "ÚĽ" "Ú˝" )
( "ąÎ" "Úľ" "ÚÁ" "ÚĆ" "Úż" "ÚŔ" "ÚÂ" "ÚĂ" "ÚÄ" "ÚĹ" "ÚÇ" "ÚČ" "ÚÉ" "ÚĘ" )
( "ąĐ" "ÚË" "ÚĚ" "ÚÍ" )
( "ąÚ" "ÚÎ" "ÚĎ" "ÚĐ" "ÚŃ" "ÚŇ" "ÚŐ" "ÚŰ" "ÚÓ" "ŰÚ" "ÚÔ" "řď" "ÚÖ" "Ú×" "ÚÝ" "ÚŢ" "ÚŘ" "Ý­" "ÚŮ" "ÚÚ" "ÚÜ" "Úß" "Úŕ" "ŰŢ" )
( "ąÝ" "Úá" "Úâ" "Úă" "Úä" "Ü§" "ŢŻ" "Úĺ" "Úć" "Úę" "Úë" "Úç" "Úč" "Úé" "Úě" "Ú÷" "Úí" "Úî" "Úď" "Úđ" "Úń" "Úň" "Úó" "Úô" "Űĺ" "Úő" "Úö" "Úř" "Úů" )
( "ąß" "Úú" "ř§" "Úű" "Úü" "Úý" "Úţ" "Űˇ" "Ű˘" "ŰŁ" "Ű¤" "ŰĄ" "Ű¦" )
( "ąć" "Ű§" "Ű¨" "Ű©" "ŰŞ" "Ű«" "Ű¬" "ř°" "Ű­" "Űµ" "ŰŔ" "ŰÁ" "Ű®" "ŰŻ" "Ű°" "Ű±" "Ű˛" "Ű¸" "Űą" "Űł" "Ű´" "Ű»" "ŰĽ" "Ű¶" "Ű·" "Űş" "Ű˝" "Űľ" "Űż" "ŰÂ" )
( "ąč" "ŰĂ" "ŰÄ" "ÝÁ" "ŰĆ" "Ýĺ" "ŰÇ" "ŰÉ" "ŰË" "ŰÖ" "ŰČ" "ŰÎ" "ŰĎ" "ŰĘ" "ŰĚ" "ŰÍ" "ŰŇ" "ŰĐ" "ŰŃ" "ŰÓ" "ŰÔ" "ŰŐ" )
( "ąé" "Ű×" "ŰŘ" "ŰŮ" "ŰÚ" "ŰŰ" "ŰÜ" "ŰÝ" "ŰŢ" )
( "ąř" "Úă" "Űß" "Úë" "Űŕ" "Űá" "Űâ" "Űć" "Űç" "Űă" "Űä" "Űĺ" "Űč" )
( "ąú" "Űé" "Űë" "Űę" "Űě" )
( "ąü" "Űí" "Űî" "Űđ" "Űń" "Űň" "Űó" "Űď" "Űő" "Űô" )
( "ąý" "Űö" "Ű÷" )
( "ş®" "Űř" "Űů" "Űú" "Űű" "Űü" "Ü˘" "Űý" "Űţ" "Üˇ" "ÜŁ" "Ü¤" )
( "şŻ" "řµ" "Ü¦" "Ü§" "Ü«" "řş" "Ü¨" "Ü©" "ÜŞ" )
( "ş°" "Ü¬" "řĚ" "Ü­" "Ü®" "ÜŻ" )
( "ş´" "Ü°" "Ü±" "Ü˛" "Üł" "Ü´" "Ţł" "Üµ" "Ü¶" "Űł" "Ü·" "Ü¸" "Üą" "Üş" "Ü»" "ÜĽ" "Ü˝" "Üľ" "Üż" "ÜŔ" )
( "ş¸" "ÜÁ" "ÜÂ" "ÜĂ" "ÜÄ" "ÜÇ" "ÜČ" "ÜÉ" "ÜĹ" "ÜĆ" "Ý«" "ÜĘ" "ÜĚ" "ÜË" "ÜÍ" "ÜÎ" "ÜĎ" "ÜĐ" )
( "şą" "ÜŃ" "ÜŇ" "Üů" "ÜÓ" "ÜÔ" "ÜŐ" "ÜÖ" "ÚŇ" "ÜÇ" "Ü×" "ÜŮ" "ŮĘ" "ÚÔ" "ÜÚ" "ÜŰ" "ÜŘ" "ÜÜ" "ÜÝ" "Üß" "ÜŢ" "Üŕ" "Üá" )
( "ş»" "Üâ" )
( "şĽ" "Üă" )
( "şŔ" "Üä" "Üĺ" "Üć" "Üč" "Üç" "Üé" "Űň" "Üę" "Üë" "Üě" "Üí" "Üď" "Üń" "Üî" "Üđ" "Üň" "Üó" )
( "şÎ" "ÝŐ" "Üő" "ÜŃ" "Üö" "Ü÷" "Üř" "Üů" "Üú" "Üű" "ŰĆ" "Üü" "Üý" "Üţ" "Ýˇ" "Ý˘" "ÝŁ" "Ý¤" "ÜÖ" "Ý¦" "Ý©" "ÝŞ" "Ý»" "Ýľ" "Ý§" "Ý¨" "Ý°" "Ý±" "Ý«" "Ýł" "Ý´" "Ý¬" "Ý­" "Ý®" "ÝŻ" "Ý˛" "řć" "ÜÝ" "Ýµ" "Ý¶" "Ý·" "Ý¸" "Ýą" "Ýş" "Üß" "ÝĽ" "Ý˝" "Ýż" "ÝŔ" )
( "şĎ" "ÝÁ" )
( "şĐ" "ÝÂ" "Ýă" "ÝĂ" "ÝÄ" "ÝĹ" "ÝĆ" "ÝÇ" "ÝÉ" "ÝĘ" "ÝĚ" "ÝČ" "ÝË" "ÝÍ" "ÝŇ" "ÝÎ" "ÝĎ" "ÝĐ" "ÝŃ" "ÝÓ" "ÝÔ" )
( "şŇ" "ÝŐ" "ÝÖ" "Ý×" "ÝŘ" "ÝŮ" "Ýó" )
( "şŘ" "ÝÚ" "ÝŰ" "ÝÜ" "ÝÝ" "ÝŢ" "Ýß" )
( "şń" "ÝŐ" "Ýŕ" "Ýá" "Űř" "Ýâ" "Ýă" "Ýä" "Üú" "Ýĺ" "Ýć" "Ýç" "Ýë" "Ýó" "Ýô" "Ţ©" "Ýč" "Ýé" "Ýę" "Ýě" "Ýţ" "Ţˇ" "Ţ˘" "Ýí" "Ýî" "Ýď" "Ýń" "Ýň" "Ýđ" "Ýő" "ŢŁ" "Ýö" "Ý÷" "Ýř" "Ýů" "Ýú" "ŢĄ" "Ýű" "Ýü" "Ýý" "Ţ¤" "Ţ¦" "Ţ§" "Ţ¨" "ÝÓ" "ŢŞ" "Ţ«" "Ţ¬" )
( "şó" "Ţ­" "Ţ®" "ŢŻ" "Ţł" "Ţ´" "Ţµ" "Ţ°" "Ţ±" "Ţ˛" "Ţ¶" "Ţ·" "Ţ¸" "Ţą" "ëË" "Ţş" )
( "şů" "Ţ»" "ŢĽ" "Ţ˝" "ů§" "Ţľ" )
( "»ç" "Ţż" "ŢŔ" "ŢÁ" "ŢÂ" "ŢÄ" "ŢĂ" "ŢĹ" "ŢĆ" "ŢÇ" "ŢČ" "ŢÉ" "ŢĘ" "ŢË" "ŢĚ" "ŢÍ" "ŢÎ" "ŢĎ" "ŢĐ" "ŢŃ" "ŢŇ" "ŢÓ" "ŢÔ" "ŢŐ" "Ţ×" "ŢŢ" "Ţß" "Ţŕ" "Ţá" "Ţâ" "Ţ÷" "ŢÖ" "ŢŘ" "ŢŮ" "ŢÚ" "ŢŰ" "ŢÜ" "ŢÝ" "ýú" "Ţí" "Ţî" "Ţă" "Ţĺ" "Ţä" "Ţć" "Ţç" "Ţč" "Ţé" "Ţę" "Ţë" "Ţě" "Ţď" "áń" "Ţđ" "Ţń" "Ţň" "Ţó" "Ţô" "Ţő" "Ţö" "ăÝ" "Ţř" "Ţů" "Ţú" )
( "»č" "Ţű" "áő" "â¦" "Ţý" "čü" "Ţţ" )
( "»ę" "ßˇ" "ß˘" "ßŁ" "ßĄ" "ß¤" "ß¦" "ßŞ" "ß§" "ß¨" "ß©" "ß«" "ß¬" )
( "»ě" "ß­" "ß®" "ßŻ" "ß°" "óů" "ß±" )
( "»ď" "ß˛" "óŃ" "ß¶" "ß´" "ßµ" "ß·" "ß¸" "ßą" )
( "»đ" "ßş" "ß»" "ßĽ" "ß˝" )
( "»ó" "ßľ" "ßż" "ßŔ" "ßÁ" "úľ" "ßÂ" "ßĂ" "ßÄ" "ßĹ" "ßĆ" "ßÇ" "ßČ" "ßÉ" "ßĘ" "ßË" "ßĎ" "÷·" "Öé" "ßĚ" "ßÍ" "ßÎ" "ßĐ" "ßŃ" "ßŇ" "ßÓ" "ßÔ" "ßŐ" "ßÖ" "ß×" "ßŘ" "ßŮ" "ßÚ" "ßŰ" "ßÜ" "»ő" "ŢÇ" "ßá" "ŢÖ" "ßŢ" "ßß" )
( "»ö" "ßŕ" "ßá" "íů" "ßâ" "Ţţ" "ßä" )
( "»ý" "ßĺ" "ßć" "ßç" "ŕý" "ßé" )
( "Ľ­" "ßę" "ßë" "ßě" "ßí" "ßî" "ßď" "ßń" "ßň" "ßđ" "ßó" "ßô" "ßő" "ßö" "ŕˇ" "ß÷" "ßř" "ßů" "ßú" "ŕŁ" "ŕ¦" "ßţ" "ßű" "ßü" "ßý" "ŕ˘" "ŕ¤" "ŕĄ" "ŕ§" "ŕ¨" "ŕ©" )
( "Ľ®" "ŕŞ" "ŕ«" "ŢŇ" "ŕ¬" "ŕ­" "ŕ±" "ŕ˛" "÷Ę" "ŕł" "ŕ®" "ŕŻ" "ŕ°" "ŕ¶" "ŕ´" "ŕµ" "Ţě" "ŕ·" "ŕ¸" )
( "Ľ±" "Đć" "ŕą" "ŕş" "ŕ»" "Ó¤" "ŕĽ" "ŕ˝" "ŕľ" "ćÉ" "óĽ" "ŕÂ" "ŕż" "ŕŔ" "ŕÁ" "ŕÍ" "ŕÎ" "ŕĂ" "ŕÄ" "ŕĹ" "ŕĆ" "ŕÇ" "ßŞ" "ŕĐ" "ŕÔ" "ü˝" "ŕČ" "ŕÉ" "ŕĘ" "ŕË" "ŕĚ" "ŕĎ" "ŕŃ" "ŕŇ" "ŕÓ" "ŕŐ" "ŕÖ" "ŕ×" "ŕŘ" )
( "Ľł" "ŕŮ" "Ěř" "ŕÚ" "ŕÜ" "ŕÝ" "ŕŢ" "ŕŰ" "ŕŕ" "ŕß" "ŕá" "ŕâ" "ŕă" "ŕä" "ŕĺ" )
( "Ľ¶" "ŕć" "ÓÂ" "ŕí" "ŕç" "ŕč" "ŕé" "ŕę" "ôÚ" "ŕë" "ŕě" )
( "Ľ·" "ă¦" "ŕî" "ŕď" "ŕđ" "ŕń" )
( "Ľş" "ŕň" "ŕó" "ŕô" "ŕő" "ŕö" "ŕú" "ŕ÷" "ŕř" "ŕů" "áŁ" "ŕű" "ŕü" "ŕý" "ŕţ" "áˇ" "á˘" "á¤" "áĄ" )
( "ĽĽ" "á¦" "ŕ»" "á§" "á©" "á¨" "áŞ" "á«" "á¬" "ŕă" "á®" )
( "ĽŇ" "Ţű" "áŻ" "á°" "á±" "á˛" "áł" "á´" "áµ" "ôý" "á·" "â¤" "á¸" "á»" "áĽ" "á˝" "áľ" "áĐ" "á¶" "áą" "ő«" "áş" "áż" "áŔ" "áĘ" "áË" "áĚ" "áÎ" "áĎ" "áÁ" "ůµ" "áÂ" "áĂ" "áÄ" "áĹ" "áĆ" "áÇ" "áČ" "áÉ" "đŰ" "áÍ" "đß" "áň" "áŃ" "áŇ" "áÓ" )
( "ĽÓ" "áÔ" "áŐ" "á×" "áÖ" "áÜ" "áŘ" "áŮ" "áÚ" "áŰ" )
( "ĽŐ" "áÝ" "áŢ" "áß" "áŕ" "áá" "áâ" )
( "ĽÖ" "×Ë" )
( "ĽŰ" "áä" "áĺ" "áç" "áć" "áę" "éĆ" "áč" "áé" "áë" )
( "Ľâ" "áě" "áî" "áí" "áď" "â¶" "áđ" )
( "Ľč" "áń" "áň" )
( "Ľö" "áó" "áô" "ęć" "ńł" "áő" "áö" "á÷" "ář" "áů" "áú" "âÖ" "áű" "áü" "áý" "âŁ" "â¤" "âŞ" "â«" "â­" "âÉ" "Óé" "âĘ" "âË" "áţ" "âˇ" "â˘" "âĄ" "â¦" "â»" "â§" "â¨" "â©" "â¬" "â®" "âŻ" "â°" "âĽ" "â˝" "âľ" "âż" "âÄ" "ë¶" "âĹ" "×Ë" "â±" "â˛" "ü˘" "âł" "áŞ" "â´" "âµ" "âŔ" "â¶" "â·" "â¸" "éŁ" "âą" "âş" "âú" "âÁ" "âÂ" "âĂ" "âĆ" "âÇ" "âČ" "őß" "âĚ" "âÍ" "âÎ" "âĎ" "âĐ" "âŃ" )
( "Ľ÷" "âŇ" "âÓ" "âÔ" "âŐ" "âÖ" "â×" "âŘ" "âŮ" "âÚ" "âŰ" "âÝ" "âÜ" )
( "Ľř" "âŢ" "âß" "âŕ" "âá" "âç" "âč" "ââ" "âî" "âă" "âä" "âĺ" "âć" "âé" "âđ" "âń" "âň" "âę" "âë" "âě" "âí" "âď" "âó" "âô" "âő" "âö" "â÷" "âř" )
( "Ľú" "âů" "âű" "âú" "âü" )
( "Ľţ" "âţ" "âý" "ăˇ" )
( "˝˝" "ăŁ" "ă˘" "ă¤" )
( "˝Ŕ" "ă¦" "ăĄ" "ă¨" "ă§" "ă©" )
( "˝Â" "ăŞ" "ă«" "ă¬" "ă­" "ă®" "ăł" "ăŻ" "ă°" "ă±" "ă˛" )
( "˝Ă" "ă´" "ăµ" "ă¶" "ă·" "ă¸" "ŢŃ" "ăą" "ăş" "ă»" "ăĽ" "ă˝" "ăľ" "đ«" "ăÄ" "ŢŮ" "ăż" "ăŔ" "ăÁ" "ăĂ" "ăÂ" "ăČ" "ăÉ" "ăĹ" "ăĆ" "ăÇ" "ăĘ" "ăË" "ăĚ" "ăÍ" "ăÎ" "ăĎ" )
( "˝Ä" "ăĐ" "ăŃ" "ăŇ" "ăÔ" "ă×" "ăÓ" "ăŐ" "ăÖ" "ăŘ" "ăŮ" "ăÚ" "ăŰ" "ăÜ" "ăÝ" "ăŢ" )
( "˝Ĺ" "ăß" "ăŕ" "ăá" "ăâ" "ăă" "ăä" "ăĺ" "ăć" "ăç" "ăě" "ăč" "ăî" "ăď" "ăđ" "ăö" "ňä" "ăé" "ăę" "ăë" "ăí" "ăń" "ăň" "ăó" "ăô" "ňă" "ňč" )
( "˝Ç" "ă÷" "ăř" "ăů" "ăú" )
( "˝É" "ăű" "ăü" "öŘ" "ăţ" "ä˘" "äŁ" "ăý" "äĄ" "ÓĆ" "ä¤" "ä¦" )
( "˝Ę" "ä§" "ä¨" "ă¦" )
( "˝Ö" "äŞ" )
( "ľľ" "ä«" )
( "ľĆ" "ä¬" "ä­" "ä®" "äŻ" "ä°" "ä±" "äą" "ä˛" "äł" "ä´" "äµ" "ä¶" "ä·" "ä¸" "äş" "ä»" "äĽ" "ä˝" )
( "ľÇ" "äľ" "äż" "äŔ" "äÁ" "äĂ" "äÄ" "äĆ" "äÇ" "äÂ" "ŐĄ" "äČ" "äÉ" "äĘ" "äË" )
( "ľČ" "äĚ" "äÍ" "äÎ" "äĎ" "äĐ" "äŃ" "äŇ" "äÓ" "äÔ" "äŐ" )
( "ľË" "äÖ" "ä×" "äŘ" "äŮ" )
( "ľĎ" "äÚ" "äŰ" "äÜ" "äÝ" "ëä" "äŢ" "äŕ" "äß" "äá" )
( "ľĐ" "ä¬" "äâ" "äă" "ää" "ËŁ" "äĺ" )
( "ľÓ" "äć" "äç" "äč" "äé" "äę" "äë" "äě" )
( "ľÖ" "äí" "äî" "Ęâ" "ýí" "äď" "äđ" "äó" "äö" "äń" "äň" "äő" "äô" "ä÷" )
( "ľ×" "äř" "äŻ" "äů" "äú" "äű" "äý" "äü" "äţ" )
( "ľŢ" "ĺˇ" "ĺ˘" "ĺŁ" "ĺ¤" )
( "ľß" "ĺĄ" "ĺ¦" "ĺ§" "ĺ¨" "ŢŇ" "ĺŞ" "Ţ÷" "ĺ©" "ŢŘ" "ĺ«" "ĺ¬" "ĺ´" "ĺ­" "ĺŻ" )
( "ľŕ" "ĺ°" "ŐÓ" "ĺ´" "ĺµ" "ĺ¶" "ĺ·" "ŐÔ" "ĺł" "ĺ¸" )
( "ľç" "ŐŐ" "ĺş" "Ő×" "ŐŘ" "ĺ˝" "ĺľ" "ĺŔ" "ĺÁ" "ĺÇ" "÷·" "ĺČ" "ĺŐ" "ĺż" "ĺÂ" "ĺĂ" "ŐŮ" "ĺĹ" "ĺĆ" "ĺÉ" "ĺĘ" "ĺË" "ĺĚ" "ĺÍ" "ŐÝ" "ĺĎ" "ŐŢ" "ĺŃ" "ßŮ" "Őß" "ĺÓ" "ĺÔ" "Őá" "ĺ×" )
( "ľî" "çî" "ĺŘ" "ĺŮ" "ĺŰ" "ĺÚ" "ĺÜ" "ĺÝ" "ä·" "ĺŢ" "ĺß" "ĺŕ" "ĺá" )
( "ľď" "ĺâ" "ĺă" "ĺä" "ĺć" "ĺĺ" "ëű" )
( "ľđ" "ĺç" "ĺč" "ĺé" "ĺę" "ĺë" "ĺě" )
( "ľó" "ĺí" "Ü˘" )
( "ľö" "ĺď" "ĺđ" "ĺń" "ĺň" "ĺó" "ĺô" )
( "ľ÷" "ĺő" "ĺö" )
( "żŁ" "ĺ÷" )
( "ż©" "ĺř" "ĺů" "Őä" "Őĺ" "Ňł" "ĺý" "Őć" "ćŁ" "Őë" "Ţ÷" "đ¶" "Őé" "ć˘" "ćĄ" "ćŞ" "ć¦" "Őě" "ć¨" "ć©" "ć«" "ć¬" "Őď" "ć®" "Őń" "Őň" "Őó" )
( "żŞ" "ć˛" "Őô" "ć´" "ŢŇ" "ćµ" "ć¶" "Őő" "Őö" "ć˝" "ćą" "ćş" "ć»" "Őů" "ćľ" )
( "ż¬" "ěÖ" "ćż" "ćŔ" "ćÁ" "ćÂ" "ćĂ" "Ň´" "ćĹ" "ćĆ" "ćČ" "ćÉ" "ćĘ" "ćĚ" "ćÍ" "ćÎ" "ćĎ" "ćĐ" "ćŃ" "Őţ" "Őü" "ćË" "ćÓ" "Öˇ" "ćŐ" "ć×" "ćÔ" "ćŘ" "Ö˘" "ÖĄ" "Ö§" "ćÚ" "ćŰ" "ćÜ" "ćÝ" "ÖŁ" "ćŢ" "ćŕ" "ŕĚ" "Ö¤" "ćâ" "ćă" "Ö¦" "ćç" "Ö¨" "âÍ" "ćé" )
( "ż­" "ÖŞ" "Ö«" "ěÖ" "ćí" "ćî" "Ö­" "ćđ" "áŞ" "Ö®" "ŕă" "ćó" )
( "ż°" "ćô" "äâ" "ÖŻ" "Ňş" "Ň·" "ćř" "Ö±" "ćú" "ćű" "ćü" "ćţ" "Öł" "ćý" "ÓÇ" "ÓĘ" "ç˘" "çŁ" "ç¤" )
( "ż±" "Ö´" "çĄ" "ç§" "ç¨" )
( "żµ" "Öµ" "Ö·" "ç«" "Ň»" "ç®" "Öş" "çŻ" "Ö»" "ç¶" "ç·" "çą" "çş" "ç»" "çľ" "ç±" "ç˛" "çł" "ç´" "çµ" "ç¸" "çĽ" "ç˝" "ÖĽ" "çŔ" "çÂ" "çČ" "çĘ" "çÁ" "çĂ" "çÄ" "çĹ" "Öľ" "ÖŔ" "çÉ" "ÖÂ" "çĚ" "ÖĂ" "çÎ" "ÖÄ" "ÖĹ" )
( "żą" "çŃ" "ÖÇ" "çŇ" "ä®" "çÔ" "çŐ" "ç×" "ŕÜ" "çŘ" "çŮ" "çÖ" "éý" "çÜ" "çÝ" "çŢ" "çÚ" "ÖÉ" "çŰ" "çŕ" "çá" "çâ" "çă" "ÖĘ" "çĺ" "ÖË" "çç" "çč" )
( "żŔ" "çé" "çę" "çë" "çě" "çí" "çď" "çî" "çđ" "çń" "çň" "čě" "çó" "çô" "çő" "çö" "çř" "çý" "çţ" "äÂ" "çů" "ĺÚ" "çú" "çű" "çü" "čˇ" "č˘" "čŁ" "éć" "č¤" "čĄ" "č¦" "ĺŕ" "č§" "č¨" )
( "żÁ" "č©" "čŞ" "č«" "äą" "č¬" "č­" )
( "żÂ" "č®" "čŻ" "čł" "č°" "č±" "č˛" )
( "żĂ" "č´" )
( "żË" "čµ" "č¶" "č·" "č¸" "čą" "čş" "č»" "čĽ" "č˝" )
( "żÍ" "čß" "çý" "čľ" "čż" "čŔ" "čÁ" "čÂ" "čĂ" "čÄ" "čĹ" )
( "żĎ" "čĆ" "čÇ" "čČ" "čË" "čÖ" "čŇ" "čÓ" "čÉ" "čĘ" "čĚ" "čÍ" "čÎ" "čÔ" "čĎ" "čĐ" "čŃ" "čŐ" "č×" )
( "żĐ" "čŘ" )
( "żŐ" "čŮ" "čÜ" "čÚ" "čŰ" "čÝ" )
( "żÖ" "čŢ" "čß" "čŕ" "čá" )
( "żÜ" "čâ" "ęÎ" "čă" "čä" "čĺ" "čŕ" "čć" )
( "żä" "Öő" "Öö" "čé" "čę" "čë" "čě" "čí" "čî" "čď" "Ö÷" "Ňă" "čň" "Öř" "čó" "ęń" "čô" "čő" "čö" "ë˘" "Ô¶" "Öů" "čř" "é¦" "ŐĄ" "čú" "Öú" "čü" "čý" "Öţ" "é«" "é¬" "é­" "Öű" "éˇ" "é˘" "Ůđ" "éŁ" "é¤" "éĄ" "é¨" "é©" "éŞ" "ë˛" "é®" )
( "żĺ" "é±" "éŻ" "é°" "éł" "é˛" "ÍŰ" "é´" )
( "żë" "éµ" "é¶" "é·" "é¸" "éą" "éş" "é»" "éĽ" "éż" "éŔ" "éÁ" "é˝" "éľ" "éÂ" "éĂ" "éÇ" "éČ" "éÄ" "éĹ" "éĆ" "éÉ" "éĘ" "éË" "×Ł" )
( "żě" "éÍ" "éÎ" "éĎ" "éĐ" "Ďˇ" "éŃ" "éŇ" "éÓ" "éÔ" "éŐ" "éÖ" "éč" "éę" "é×" "éŘ" "éŮ" "éÚ" "éŰ" "éÜ" "éă" "éä" "éć" "éç" "éÝ" "éŢ" "éß" "éŕ" "éá" "éâ" "éĺ" "éé" "éë" "éě" )
( "żí" "éí" "éî" "čó" "éô" "éď" "éđ" "éń" "éň" "éó" "éő" )
( "żî" "éö" "ę¬" "éú" "ę˘" "é÷" "éř" "éů" "ýČ" "éű" "éý" "éţ" "ęˇ" "éü" "ęŁ" "ę¤" )
( "żď" "ę§" "ęĎ" "ę˝" "ęĄ" "ę¦" )
( "żő" "ę¨" "ę©" )
( "żř" "ĚČ" "ęŞ" "ĺ÷" "ę«" "ę¬" "ę­" "ę®" "ęŻ" "ę°" "ę±" "ę˛" "ęµ" "ę¶" "ę·" "ę¸" "ęą" "ę»" "ęÁ" "ęÂ" "ę˘" "ęł" "ę´" "ęş" "ęĽ" "ę˝" "ęŔ" "ęľ" "ęż" "ęĂ" "ęÄ" )
( "żů" "čŘ" "ęĹ" "ęĆ" "ęÇ" )
( "Ŕ§" "ęČ" "ęÉ" "ęĘ" "ęË" "ęĚ" "ęÍ" "ęÎ" "ęĎ" "ęŇ" "ęĐ" "ęŃ" "ęÖ" "ęÓ" "ęÔ" "ę×" "ęŘ" "ęĄ" "ęŮ" "ęŢ" "ęÜ" "ęŐ" "ęÚ" "ęŰ" "ęÝ" "ęß" "ęŕ" )
( "ŔŻ" "ęá" "ęâ" "ęă" "ęä" "×±" "éŃ" "ęć" "ęç" "ęč" "ęé" "ęę" "ęë" "ęě" "ęî" "ęđ" "Ń×" "ęń" "ęú" "ęű" "×µ" "ęý" "×¶" "ëˇ" "ë˘" "ęí" "ęď" "ęň" "ęó" "Ňî" "ęö" "ęő" "ęů" "ęř" "ëŁ" "×¸" "ëĄ" "ë­" "ë´" "ëµ" "ë¶" "ë¦" "×ş" "ë¨" "×Ľ" "ë®" "Ňď" "ë«" "éŁ" "ëż" "ë¬" "ëŻ" "ë°" "ë±" "ë˛" "ëł" "ë·" "ë¸" "ëą" "âĚ" "×ľ" )
( "Ŕ°" "×ż" "ëĽ" "×Á" "×Ŕ" "ëŔ" "ëľ" "ńÔ" "ëż" )
( "Ŕ±" "×Ă" "ëĂ" "Đ˛" "ëÄ" "ëĹ" "×Ä" "×Ĺ" "ëČ" "ëĘ" "ëÉ" "ëË" "×Ç" "ëÍ" "ëÎ" )
( "Ŕ˛" "ëĎ" "ëĐ" "ëŃ" "×Ë" "ëÓ" )
( "Ŕ¶" "ëŐ" "×Ě" "ëÔ" "ëÖ" "ë×" )
( "Ŕş" "ëŮ" "ŃŞ" "ëß" "ëÚ" "ëŰ" "ëÜ" "ĺë" "ëÝ" "ëŢ" )
( "Ŕ»" "ëŕ" )
( "Ŕ˝" "ëá" "ëâ" "ëä" "ëă" "ëĺ" "ëć" )
( "Ŕľ" "ëç" "ëč" "ëé" )
( "ŔŔ" "ëę" "ëë" "ëě" "ëí" )
( "ŔÇ" "ëî" "ëď" "ëđ" "ëń" "ëô" "ëň" "ëó" "ëő" "čŕ" "ëö" "ëű" "ë÷" "ëř" "ëů" "ëú" "ä¶" "ëü" "ëý" "ëţ" "ěˇ" "ě˘" "ŃÄ" )
( "ŔĚ" "ěŁ" "ě¤" "ěĄ" "××" "÷»" "×Ů" "ě¨" "ĺý" "ě©" "×Ű" "ě«" "ě¬" "ě­" "ě®" "Ňú" "ăż" "ć¶" "×Ý" "×Ţ" "ěł" "ě´" "×â" "ěľ" "ěż" "ěÄ" "ě¶" "ě·" "×ĺ" "ěą" "ěş" "×ë" "ě»" "ěĽ" "ě˝" "Ţď" "×ę" "ěÂ" "ěĂ" "×ě" "×î" "ăÝ" "ěÇ" "ěČ" )
( "ŔÍ" "Ňű" "Ňü" "ěË" "ěĚ" "ěÎ" "ěÍ" "ěĎ" "ěĐ" )
( "ŔÎ" "ěŃ" "ěŇ" "ěÓ" "ěÔ" "×đ" "ěÖ" "ě×" "ěŘ" "ěŮ" "ěÚ" "ěÜ" "×ń" "×ö" "ěŰ" "×ň" "×ó" "ěŕ" "×ô" "ěß" "ěâ" "ěă" "ěĺ" "ěć" "×÷" "×ř" )
( "ŔĎ" "ěé" "ěę" "ěë" "ěě" "ěî" "ěí" "ň÷" "ěď" "ěđ" "ěń" )
( "ŔÓ" "ěň" "ěó" "ěô" "ěő" "×ú" "ěö" "×ů" "ěű" "ěů" "×ü" "ěü" )
( "ŔÔ" "ěý" "ěţ" "Řˇ" "Ř˘" "ŘŁ" )
( "Ŕ×" "í¤" "íĄ" "í¦" "í§" )
( "ŔÚ" "í¨" "í©" "íŞ" "í«" "í¬" "í­" "í®" "íŻ" "í˛" "í°" "í±" "íł" "í´" "íş" "íĽ" "îÉ" "í˝" "íľ" "ó´" "íµ" "í¶" "í·" "í¸" "îÝ" "îß" "íą" "í»" "íż" "íŔ" "íÁ" "î±" "î˛" )
( "ŔŰ" "íÂ" "íĂ" "íÄ" "íĹ" "íĆ" "íÇ" "íČ" "íÉ" "íË" "íĘ" "íĚ" "ő˛" "őł" "íÍ" "íÎ" )
( "ŔÜ" "íĎ" "íŇ" "íĐ" "íŃ" "íÓ" )
( "Ŕá" "íÔ" "íÖ" "íŐ" "í×" "íŘ" "íŮ" )
( "Ŕâ" "íÚ" )
( "Ŕĺ" "íŰ" "íÜ" "íÝ" "íŢ" "íß" "íŕ" "íá" "íâ" "íă" "íä" "íĺ" "íď" "îˇ" "íć" "íç" "íó" "íô" "íč" "íé" "íę" "íë" "íě" "íí" "ßŇ" "íđ" "íö" "í÷" "íř" "íů" "íú" "íń" "íň" "íő" "íű" "íü" "íý" "íţ" )
( "Ŕç" "î˘" "îŁ" "î¤" "îĄ" "ďŔ" "î¦" "îŞ" "î«" "î§" "î¨" "î©" "î¬" "î­" "î®" "îŻ" "î°" "î±" "î˛" )
( "Ŕď" "îł" "ďé" "î´" "îµ" "î¶" )
( "Ŕú" "ó¦" "î¸" "î·" "îą" "îş" "î»" "îĽ" "î˝" "îÁ" "îÂ" "îĂ" "îÄ" "îĐ" "îľ" "îż" "îŔ" "îČ" "îÉ" "îĘ" "îË" "îĎ" "îĹ" "îĆ" "îÇ" "îĚ" "đł" "îÍ" "îÎ" "îŃ" "îŇ" )
( "Ŕű" "îÓ" "îÔ" "îŐ" "îÖ" "đŔ" "î×" "îŮ" "îÚ" "îŘ" "íł" "íË" "îâ" "íľ" "îč" "îé" "îę" "îÜ" "îÝ" "îŢ" "îß" "îŕ" "îá" "îă" "îä" "îĺ" "îć" "îç" "îë" )
( "Ŕü" "îě" "îí" "îî" "îď" "îđ" "îň" "îń" "×Ř" "îó" "îô" "îő" "îö" "î÷" "îř" "îů" "îţ" "îú" "îű" "îü" "îý" "ďˇ" "ď˘" "ďŁ" "ď¤" "ďĄ" "ď¦" "ď§" "ď¨" "ď©" "ďŞ" "ď«" "ď¬" "ď­" "ď®" "ďŻ" "ď°" "ď±" "ňĺ" "ď˛" "ńć" "ďł" "ď´" "ďµ" "ď¶" )
( "Ŕý" "ď·" "ďą" "ďş" "ńŢ" "ď¸" "ńč" "ď»" "ďĽ" "ď˝" "ďľ" )
( "Áˇ" "ďż" "ďŔ" "ďÁ" "ďÂ" "ďĂ" "ďÄ" "ďĹ" "ďĆ" "ďÇ" )
( "Á˘" "ďČ" "ďÉ" "ă¨" "ďĘ" )
( "Á¤" "ďË" "ďĚ" "ďÍ" "ďĎ" "ďÎ" "ďĐ" "ďŃ" "ďŇ" "ďÓ" "ďÔ" "ďŐ" "ďÖ" "ď×" "ďŘ" "ďâ" "ďă" "ďä" "ďĺ" "ďć" "ďç" "ď÷" "ďŮ" "ďÚ" "ďŰ" "ďÝ" "ďÜ" "ďŢ" "ďß" "ďŕ" "ďá" "ďč" "ďé" "ďę" "ôę" "ďë" "ďě" "ďí" "ďî" "ďď" "ďđ" "ďń" "ďň" "ďó" "ďô" "ďő" "ďö" "ďř" "ďů" "ďú" "ďű" "ďü" "ďý" "ďţ" "đˇ" "đ˘" "đŁ" )
( "Á¦" "đ¤" "đĄ" "đ¦" "đ§" "đ¨" "đ©" "đŞ" "ďą" "đ«" "đ­" "đ¶" "đ·" "đ°" "đ¬" "ěż" "đ±" "đ®" "đŻ" "đ˛" "đł" "ôô" "đ´" "đµ" "đ¸" "đą" "đş" )
( "Á¶" "ó¦" "đ»" "đĽ" "đ˝" "đľ" "áŻ" "îÔ" "đż" "đŔ" "đÁ" "Óű" "đÂ" "đĂ" "đĚ" "đÍ" "đć" "ÔÄ" "đÄ" "đĹ" "đĆ" "đÇ" "đČ" "đÉ" "đĘ" "đË" "áż" "đĎ" "đÎ" "đĐ" "đŃ" "âľ" "đÝ" "đă" "đä" "đŇ" "đÓ" "đÔ" "đŐ" "đÖ" "đ×" "đŘ" "đŮ" "đÚ" "đŰ" "đÜ" "đŢ" "đß" "đŕ" "đá" "đâ" "đĺ" "óą" "óş" "đç" "đč" )
( "Á·" "đé" "đę" "đë" "đě" )
( "Á¸" "đí" "đî" )
( "Áą" "đď" "đđ" "đń" )
( "Áľ" "đň" "đó" "đô" "đő" "đř" "đö" "đţ" "đ÷" "đů" "đú" "đű" "đü" "đý" "ńˇ" "ń˘" "ńŁ" "ń¤" )
( "ÁÂ" "ńĄ" "ń¦" "ń§" "ń¨" "ń©" )
( "ÁË" "ńŞ" )
( "ÁÖ" "ń«" "ń¬" "ń­" "ń®" "ń°" "ń˛" "ń±" "öň" "ńł" "ń´" "ńŻ" "ńµ" "ń¶" "ń·" "ńĽ" "ń˝" "ńľ" "ńż" "đé" "ń¸" "ń°" "ńą" "Ôâ" "ńş" "ń»" "ńŔ" "ńÁ" "ńÎ" "ńÂ" "ńĂ" "ńÄ" "ńĹ" "ńĆ" "ńÇ" "ńČ" "ńÉ" "ńĘ" "đŕ" "ńË" "đë" "ńĚ" "ńÍ" "ńĐ" "ńĎ" "ńŃ" "ńŇ" )
( "Á×" "ńÓ" "ńÔ" )
( "ÁŘ" "ńŐ" "ńÖ" "ń×" "ńŘ" "ńŮ" "đî" "Ôę" "ńÚ" "ńÝ" "ńŢ" "ńß" "ńŰ" "ńÜ" "ńŕ" "ńä" "Ôí" "ńĺ" "ńá" "ńâ" "âí" "ńă" "ńć" "ńç" )
( "ÁŮ" "ńč" )
( "Áß" "ńé" "ńę" "ńë" "ńě" )
( "Áď" "öÎ" "ńí" )
( "Áń" "ńî" )
( "Áó" "ńđ" "ńď" "ńń" "ňý" )
( "Áő" "ăŞ" "ńň" "ńó" "ńő" "ńô" "ńö" "ńú" "ń÷" "ńř" "ńů" "ńű" "ńü" )
( "Áö" "ńý" "ńţ" "ňˇ" "ň˘" "ňŁ" "ňĄ" "ň¦" "ň®" "ňŻ" "ň°" "ň¤" "ň§" "ň¨" "ň©" "ňŞ" "ň¶" "ň·" "ň«" "ň¬" "ň­" "ä«" "ňş" "ňą" "ňŔ" "ň±" "ň˛" "ňł" "Ń¶" "ň´" "ňµ" "Ń˝" "ň¸" "ň»" "ňĽ" "ň˝" "ňő" "ňľ" "ňż" )
( "Á÷" "ňÁ" "ňÂ" "ňĂ" "ňÄ" "ňĹ" )
( "Ář" "ňĆ" "ňÇ" "îó" "ňČ" "ňÉ" "ňĘ" "ňĐ" "ňŃ" "ňć" "ňç" "ňĚ" "ňË" "ňÍ" "ňÎ" "ňĎ" "ňŇ" "ňÓ" "ňÔ" "ňŢ" "ôŔ" "ňä" "Ě´" "ňŐ" "ňÖ" "ň×" "ňŘ" "ňŮ" "ňÚ" "ňß" "ňÜ" "ňŰ" "ňÝ" "ňŕ" "ňá" "ňâ" "ňă" "ňĺ" "ňč" )
( "Áú" "ěę" "ňé" "ňę" "ňë" "ňě" "ňí" "ňó" "ňî" "ňď" "ň÷" "ňđ" "ňń" "ňň" "ňô" "ňő" "ňö" )
( "Áü" "ÜÔ" "ňř" "ňů" )
( "Áý" "ä§" "ňű" "ëç" "ňü" "ńď" "ňý" "ňţ" "óˇ" "ó˘" )
( "Âˇ" "óŁ" "óĄ" "ó¤" )
( "Â÷" "ó¦" "ó§" "ó¨" "ó©" "óŞ" "ó«" "ó¬" "ó­" "ó®" "Ňţ" "ó´" "óŻ" "ó°" "ó˛" "Ëç" "óű" )
( "Âř" "őµ" "óµ" "đÂ" "ó¶" "îĘ" "ó¸" "îĆ" "ó·" "óą" "óş" "ó»" )
( "Âů" "Íú" "óĽ" "ó˝" "óľ" "óż" "óŔ" "óÁ" "óÂ" "óÄ" "óĂ" "óĹ" "óĆ" "óÇ" "óČ" "óÉ" "óĘ" "ŕ×" )
( "Âű" "óË" "óĚ" "óÍ" "óÎ" "óĎ" )
( "Âü" "óĐ" "óŃ" "óŇ" "íĎ" "óÓ" "óŐ" "óÔ" "óÖ" "ó×" "óŘ" "óŮ" )
( "Ă˘" "óÚ" "óŰ" "óÜ" "óÝ" "óŢ" "óß" "óŕ" "óá" "óç" "óč" "óé" "óâ" "óă" "óä" "óĺ" "óě" "óć" "óî" "óď" "őÇ" "óę" "óë" "óí" )
( "Ă¤" "óđ" "óń" "óň" "óó" "ó¬" "óô" "óő" "ăĂ" "óř" "óů" "óö" "ó÷" "ôˇ" "óú" "óű" )
( "ĂĄ" "óü" "óý" "óţ" "îá" "ôˇ" )
( "Ăł" "ô˘" "ôŁ" "ô¤" "ßü" "ôĄ" )
( "Ă´" "ô¦" "í©" "ô¨" "ô©" "ôŞ" "ô¬" "ô­" "ôŻ" "ôł" "ô«" "ô®" "ô±" "ô°" "őě" "ô˛" "ô´" )
( "Ăµ" "Íú" "Ó˘" "ôµ" "ô¶" "ô·" "ô¸" "ôą" "ôş" "ôĽ" "ôĆ" "ô»" "ô˝" "ôŔ" "ôĂ" "ôľ" "ôż" "ôÁ" "ôÂ" "ôÄ" "ôĹ" "ôÇ" )
( "Ă¶" "ôČ" "ôÉ" "ôĘ" "ôË" "ôĚ" "ôÍ" "ôÎ" "ôĎ" "ôĐ" "ôŃ" )
( "Ă·" "ôŇ" "ôÓ" "ôÔ" "ôŐ" "ôÖ" "ô×" "ôŘ" "ôŮ" "ôÚ" "ôŰ" )
( "Ă¸" "ôÜ" "ôÝ" "ôŢ" "ôß" "ôŕ" "ôá" "ôâ" "ă¨" "ôă" "ôä" "ôĺ" )
( "Ă»" "ôć" "ôč" "ôç" "ôę" "ôé" "ôë" "ôě" "ôí" )
( "ĂĽ" "ď·" "ôď" "ô¨" "ôŢ" "ôń" "ôň" "ôđ" "ôő" "ôö" "ôó" "ôô" "ô÷" )
( "ĂĘ" "ôř" "Ţű" "ôů" "ôú" "ôű" "ôü" "ôý" "ő«" "ôţ" "őˇ" "ő˘" "őŁ" "ő¤" "őĄ" "ő­" "ő®" "őŻ" "ő¦" "ő§" "ő¨" "ő©" "őŞ" "ő¬" "ő°" "ő±" "ő˛" "őł" "ő´" )
( "ĂË" "őµ" "ő¶" "áŐ" "ô«" "â¦" "ő·" "ő¸" "őą" "őş" "őŮ" "đě" )
( "ĂĚ" "ő»" "őĽ" "őľ" "ő˝" )
( "ĂŃ" "é¶" "őż" "őŔ" "őÁ" "őĂ" "őÄ" "őÂ" "őÇ" "őĹ" "őĆ" "őČ" "×Ł" )
( "ĂÔ" "őÉ" "ńč" )
( "ĂÖ" "őĘ" "őË" "őĚ" )
( "Ăß" "őÍ" "őÎ" "őĎ" "őÓ" "őŰ" "Óé" "âĘ" "ý®" "őĐ" "őŃ" "÷Ů" "őŇ" "ő×" "őÚ" "őÔ" "őŐ" "őÖ" "őŘ" "őŮ" "őÜ" "őÝ" "őß" "őŢ" "őŕ" "őá" "őâ" "őă" )
( "Ăŕ" "őä" "âŘ" "ęö" "őë" "őď" "őĺ" "őć" "őç" "őč" "őé" "őę" "őě" "őí" "őî" )
( "Ăá" "őđ" "őń" "őň" )
( "Ăâ" "őó" "őô" "őő" )
( "Ăć" "őö" "őř" "ő÷" "őů" "őú" "őű" )
( "Ăé" "őü" "őý" "őţ" "öˇ" )
( "Ăë" "ö˘" "öŁ" "ö¤" "öĄ" "ö¦" "öŞ" "ö§" "ö¨" "ö©" "ö«" "ö¬" "ö­" "ö®" "öŻ" )
( "Ăř" "ö±" "ö°" "ö˛" "öł" "ö´" "ňĂ" )
( "Ăţ" "öµ" )
( "Äˇ" "ö¶" "ö·" "ö¸" "öą" "ó«" "öş" "ě¬" "óŁ" "ö˝" "öľ" "ň¤" "ö»" "öĽ" "ăŐ" "öż" "öŔ" "öÁ" "öÂ" "ňÁ" "öĂ" "öÄ" "öÇ" "âí" "öĹ" "öĆ" "ňÄ" "öČ" "öÉ" "ăŰ" "öĘ" "öË" "öĚ" "öÍ" )
( "Ä˘" "öÎ" "öĎ" "öĐ" )
( "ÄŁ" "öŃ" )
( "ÄĄ" "öŇ" "öÔ" "öÓ" )
( "Ä§" "öŐ" "öÖ" "öŘ" "öŮ" "ňř" "ö×" "öÚ" "öŰ" "öÜ" "öÝ" )
( "Ä¨" "öŢ" )
( "ÄŞ" "öß" "öŕ" )
( "Äč" "öá" )
( "Ĺ¸" "öâ" "öă" "öä" "öĺ" "öć" "öç" "öč" "öé" "öí" "âÉ" "öę" "öë" "öě" "öî" "öď" )
( "Ĺą" "öđ" "öń" "öň" "öó" "Óř" "öő" "öö" "ö÷" "öú" "öű" "öř" "öů" "öý" "öü" "öţ" "÷ˇ" "ŰŢ" )
( "Ĺş" "ÓŁ" "÷˘" "÷Ł" "÷¤" "÷Ą" "÷¦" "÷¨" "÷§" "÷©" "ăđ" "÷Ş" "÷«" )
( "Ĺ»" "÷¬" "÷­" "áŞ" "ŕă" )
( "Ĺ˝" "÷®" "÷Ż" "÷°" "÷±" )
( "Ĺľ" "÷˛" "÷ł" "÷´" )
( "ĹÁ" "÷µ" "÷¶" "÷·" "÷ą" "ÓŘ" )
( "ĹÂ" "÷ş" "÷»" "÷Ľ" "÷Ŕ" "÷Ć" "÷˝" "÷ľ" "÷Ă" "÷­" "÷ż" "÷Á" "÷Ä" "áŞ" "÷Â" "÷Ĺ" "÷Ç" "öî" )
( "ĹĂ" "÷Č" "÷É" "÷Ę" )
( "ĹĘ" "÷Ë" )
( "ĹÍ" "÷Ě" )
( "Ĺä" "÷Í" "÷Î" "÷Ď" "÷Đ" )
( "Ĺë" "÷Ń" "÷Ó" "÷Ň" "÷×" "÷Ô" "÷Ő" "÷Ö" )
( "Ĺđ" "÷Ř" "őĎ" "ÔÄ" "÷Ú" "÷Ů" "ÔČ" "÷Ü" "őÚ" "÷Ű" "őŕ" "÷Ý" )
( "Ĺő" "÷Ţ" "÷ß" "÷ŕ" "ęđ" "÷á" "÷â" "÷ă" )
( "ĆŻ" "÷ä" "÷ĺ" "Óč" )
( "Ć´" "÷ć" )
( "ĆÄ" "÷ç" "÷č" "÷é" "÷ę" "÷ë" "÷ě" "÷î" "÷ď" "ů®" "÷í" "÷đ" "÷ń" "÷ô" "Űă" "÷ň" "Úň" "÷ó" "÷ő" "÷ö" )
( "ĆÇ" "÷÷" "Úă" "÷ř" "řˇ" "÷ů" "÷ú" "÷ű" "÷ü" "Ü©" "÷ý" "÷ţ" )
( "ĆČ" "ř˘" "řŁ" "ř¤" )
( "ĆĐ" "řĄ" "ř¦" "ř§" "ř©" "řŞ" "ř¬" "ř¨" "řË" "ř«" "ř­" "ř®" "řŻ" )
( "ĆŘ" "úű" "íä" "ř°" "ř±" "Ű±" "řł" "ř˛" )
( "ĆÚ" "ř´" )
( "Ćí" "řµ" "ř¶" "ř·" "ř¸" "řĽ" "řą" "řş" "ř»" "Ü©" "ÜŞ" "ř˝" "řľ" )
( "Ćď" "řż" )
( "Ćň" "řŔ" "řÁ" "řÂ" "řĂ" "ÝÝ" "řÄ" "ÜŞ" )
( "Ćó" "řĹ" "řĆ" "řÇ" "řČ" "řÉ" "řÎ" "řĘ" "řË" "řĚ" "Ü˘" "řÍ" )
( "Ć÷" "řĎ" "řĐ" "řŃ" "řŇ" "řÓ" "řÔ" "řŐ" "řÖ" "ř×" "Ý¦" "řŘ" "řŮ" "řÚ" "řÜ" "řÝ" "řŰ" "ří" "řŕ" "řá" "řâ" "řă" "řä" "řç" "řŢ" "řß" "řĺ" "řć" "řč" "řé" "řę" )
( "Ćř" "řë" "řî" "řŰ" "ří" "řď" "řđ" )
( "Ćú" "Üă" )
( "Ćý" "ÇĄ" "řń" "řň" "řó" "řô" "ř÷" "řő" "řö" "Ý´" "řř" "řů" "řú" "řű" "řý" "řü" "řţ" )
( "Ç¬" "ÝÂ" )
( "Ç°" "ůˇ" "ů˘" )
( "Çł" "ůŁ" "ů¤" "ůĄ" "ů¦" "ů§" )
( "ÇÇ" "ů¨" "ů©" "÷î" "ů®" "ů­" "ůŞ" "ů«" "÷ó" "ů¬" "÷ő" )
( "ÇĘ" "ÝÖ" "ůŻ" "ů°" "ÝŮ" "ů˛" "ů±" "ůł" "ů·" "ů´" "ůµ" "ů¶" "ů¸" )
( "ÇĚ" "ůą" "řë" "Űň" "ůş" )
( "ÇĎ" "ů»" "ůĽ" "ĘŁ" "ů˝" "ůľ" "ůż" "ůÁ" "ůŔ" "ůÂ" "űŘ" "ůĂ" "ůĆ" "ůÄ" "ůĹ" "ůÇ" "ůČ" )
( "ÇĐ" "ůÉ" "ůĘ" "ůË" "ůĚ" "ůÍ" )
( "ÇŃ" "ůÎ" "ůĎ" "ůĐ" "ůŇ" "ůÓ" "ůÔ" "ůŐ" "Ęű" "ůÚ" "ůŃ" "ůÖ" "ů×" "ůŘ" "ůŮ" "ůŰ" )
( "ÇŇ" "ůÜ" "úŞ" "Ęé" "ůÝ" )
( "ÇÔ" "ůŢ" "ůß" "ůŕ" "ůá" "ůâ" "ůä" "Ő˝" "ůč" "ůă" "ůĺ" "ůć" "ůç" "ůé" )
( "ÇŐ" "ůę" "ůë" "ůđ" "ËĎ" "ůě" "ůí" "ůî" "ůď" )
( "Ç×" "ůń" "ůň" "ůó" "ůô" "ůő" "ůö" "ů÷" "ůú" "ůű" "Ë˝" "ůý" "ůř" "ůů" "ůü" "ůţ" "úĽ" "úŁ" )
( "ÇŘ" "ú¤" "úĄ" "ú¦" "ú§" "ú¨" "ú©" "úŞ" "ú«" "ú­" "ú®" "ú¬" "úł" "ËĘ" "úŻ" "ú°" "ú±" "ú˛" "ú´" "úµ" )
( "ÇŮ" "ú¶" "ú·" )
( "Çŕ" "ú¸" "úą" "úş" "ú»" "úĽ" )
( "Çâ" "ú˝" "úľ" "úż" "úÁ" "úŔ" "úÂ" "úĂ" "úÄ" "úĹ" )
( "Çă" "úĆ" "úÇ" "úČ" "úÉ" )
( "Çĺ" "úĘ" "úË" "úĚ" "úÍ" )
( "Çć" "úÎ" )
( "Çč" "úĎ" "úĐ" )
( "Çő" "ć˛" "úŃ" "úŇ" "úÓ" "úÔ" )
( "Çö" "úŐ" "úÖ" "ú×" "úÚ" "úŘ" "úŮ" "úŰ" "úÝ" "úŢ" "úÜ" "úß" "úŕ" "úá" "úâ" "úă" "úä" "úĺ" "Ě¸" "úç" "úč" "úé" )
( "Ç÷" "úę" "úë" "úě" "úí" )
( "Çř" "úî" "ĚĹ" )
( "Çů" "úď" "úđ" "úń" "úň" "úó" "ńđ" "úô" "úő" "ůđ" "úö" "ú÷" "úř" "úů" "úú" )
( "Çü" "úű" "úü" "úý" "úţ" "űˇ" "ű˘" "ű¤" "űĄ" "ű®" "ůů" "űŁ" "ű¦" "ĚŢ" "ű§" "ű¨" "űŞ" "ű­" "ű«" "ű¬" "űŻ" "ű°" )
( "Çý" "ýĄ" "ű±" "ű˛" "űł" "ű´" "űµ" "ű¶" "ű·" "ű¸" "űą" )
( "ČŁ" "űş" "ű»" "űĽ" "ű˝" "űľ" "űż" "űŔ" "űÁ" "Ůä" "űÇ" "űČ" "űÉ" "űĘ" "űË" "űÍ" "űĚ" "űÎ" "űĎ" "ýô" "űÂ" "űĂ" "űÄ" "űĹ" "ÍĽ" "ű×" "űĆ" "űĐ" "űŃ" "űŘ" "űŮ" "űÚ" "űŇ" "űÓ" "űÔ" "ü®" "űŐ" "űÖ" "űŰ" "űÜ" "űÝ" "úÉ" "űŢ" "űß" "űŕ" "ÍŇ" "űá" "űâ" )
( "Č¤" "űă" "űä" "űĺ" )
( "ČĄ" "űć" "űč" "űé" "űç" "Íâ" "űę" "űë" )
( "Č¦" "űí" "űě" "űî" )
( "Č«" "űď" "üó" "űđ" "űň" "űó" "űń" "űô" "űő" "űö" "ű÷" "űř" )
( "Č­" "űů" "űú" "űű" "űü" "űý" "üŁ" "ü¤" "űţ" "üˇ" "ü˘" "üĄ" "ü¦" "ü§" "ü¨" )
( "Č®" "ü©" "üŞ" "ü«" "űÍ" "ü­" "ü¬" "ü®" )
( "ČŻ" "üŻ" "Đć" "ü°" "ü±" "ü˛" "üł" "üµ" "üą" "ü´" "ü·" "ü¸" "ü¶" "üş" "ü»" "ü˝" "úß" "üĽ" "üľ" "üż" )
( "Č°" "üŔ" "Íč" "üÁ" "üÂ" "üĂ" "ęĆ" "üÄ" )
( "Č˛" "üĹ" "üĆ" "üÇ" "üČ" "üÉ" "üĘ" "üË" "üĎ" "üĐ" "üŃ" "üŇ" "üŰ" "üĚ" "üÍ" "üÎ" "üÓ" "üÔ" "ŘÓ" "ŘÔ" "üŘ" "üÚ" "üŐ" "üÖ" "ü×" "üŮ" "üÜ" )
( "Č¸" "üÝ" "üŢ" "ÎŐ" "üß" "üŕ" "üá" "üâ" "üă" "üç" "üč" "üę" "üä" "üĺ" "üě" "üć" "üé" "üí" "üë" "üî" "üď" "üđ" "Čą" "üń" "üň" "űţ" )
( "Čľ" "üó" "üô" "ýĽ" "üő" )
( "Čż" "üö" "ü÷" "üř" "čő" "üý" "üţ" "üů" "üú" "üű" "ý˘" "üü" "ýÎ" "ýˇ" "ýŁ" "ý¤" )
( "ČÄ" "ýĄ" "ý¦" "ý§" "ý¨" "ý©" "ýŞ" "ý«" "ý¬" "ý­" "Ůä" "ý®" "ýŻ" "ý°" "ý±" "ö«" )
( "ČĆ" "ý˛" "ýł" "ý´" "ýµ" "ý»" "ý¸" "ý¶" "ý·" "ýą" "ýş" "âř" )
( "ČË" "ýĽ" )
( "ČÍ" "ý˝" "ýľ" "Ńî" "ýż" "ýŔ" )
( "ČŃ" "ýÁ" "ýÂ" "ýĂ" )
( "ČÖ" "ýÄ" "ýĹ" "ýĆ" "ýÇ" "ýČ" "ęÜ" "ýÉ" "ýĘ" "ýË" )
( "ČŢ" "ýĚ" "öĺ" "ýÍ" "ýÎ" "ýĎ" "ýĐ" )
( "Čá" "ýŃ" "ýŇ" "ýÓ" )
( "Čä" "ýÔ" "ýŐ" "ýÖ" "ý×" "ýŘ" )
( "Čć" "ýŮ" )
( "Čç" "ýÚ" "ýŰ" "ýÜ" "ýÝ" )
( "Čę" "ýŢ" "ýß" "Ń©" "ýŕ" "ýá" )
( "Čě" "ýâ" "ýă" "ýä" )
( "Čí" "ýĺ" "ýć" "ýç" "ýč" )
( "Čď" "ýé" )
( "Čń" "ýę" "ýë" "ýě" "ýí" "ýî" "ýď" "ýđ" "ýń" "ýó" "ëň" "ýň" "ýô" "Đţ" "ýő" "ýö" "ýů" "ý÷" "ýř" "ýú" "ýű" "ýü" "ýý" "×í" )
( "Čú" "ýţ" )
    ); 
);defun

(defun getum1()
  '(
("°ˇ" "ůĽ" "Ęˇ" "Ę˘" "ĘŁ" "Ę¤" "ĘĄ" "Ę¦" "Ę§" "Ę¨" "Ę©" "ĘŞ" "Ę«" "Ę¬" "Ę®" "Ę­" "ĘŻ" "Ę°" "Ę±" "Ę´" "Ęµ" "ĘĽ" "Ę˛" "Ęł" "Ę¶" "Ę·" "Ę¸" "Ęą" "Ęş" "Ę»" "Ę˝" )
    );
);defun
