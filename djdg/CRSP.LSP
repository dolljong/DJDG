(defun c:crsp(/ ent1 ent2 crsp)
(setq ent1 (entget (car (entsel "Select first object: "))))
(setq ent2 (entget (car (entsel "Select second object: "))))
(setq pt110 (cdr (assoc 10 ent1)))
(setq pt111 (cdr (assoc 11 ent1)))
(setq pt210 (cdr (assoc 10 ent2)))
(setq pt211 (cdr (assoc 11 ent2)))
(setq crsp (inters pt110 pt111 pt210 pt211 nil))
)
