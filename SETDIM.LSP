(defun c:setdim()
 (setvar "DIMADEC"         0)
 (setvar "DIMALT"        0)
 (setvar "DIMALTD"        2)
 (setvar "DIMALTF"       25.4000)
 (setvar "DIMALTTD"       2)
 (setvar "DIMALTTZ"       0)
 (setvar "DIMALTU"        2)
 (setvar "DIMALTZ"        0)
 (setvar "DIMAPOST"       "")
 (setvar "DIMASO"         1)
 (setvar "DIMASZ"       0.800)
 (setvar "DIMAUNIT"       0)
 (setvar "DIMBLK"       "DOT")
 (setvar "DIMBLK1"       "DOT")
 (setvar "DIMBLK2"       "DOT")
 (setvar "DIMCEN"       0.090)
 (setvar "DIMCLRD"       1)
 (setvar "DIMCLRE"       1)
 (setvar "DIMCLRT"       7)
 (setvar "DIMDEC"       3)
 (setvar "DIMDLE"       0.000)
 (setvar "DIMDLI"       0.380)
 (setvar "DIMEXE"       2.000)
 (setvar "DIMEXO"       10.000)
 (setvar "DIMFIT"       5)
 (setvar "DIMGAP"       1.250)
 (setvar "DIMJUST"       0)
 (setvar "DIMLFAC"       0.0010)
 (setvar "DIMLIM"       0)
 (setvar "DIMPOST"       "")
 (setvar "DIMRND"       0.001)
 (setvar "DIMSAH"       1)
 (setvar "DIMSCALE"       1.000)
 (setvar "DIMSD1"       0)
 (setvar "DIMSD2"       0)
 (setvar "DIMSE1"       0)
 (setvar "DIMSE2"       0)
 (setvar "DIMSHO"       1)
 (setvar "DIMSOXD"       0)
; (setvar "DIMSTYLE"       "STANDARD")
 (setvar "DIMTAD"       1)
 (setvar "DIMTDEC"       3)
 (setvar "DIMTFAC"       0.0720)
 (setvar "DIMTIH"       0)
 (setvar "DIMTIX"       1)
 (setvar "DIMTM"       0.000)
 (setvar "DIMTOFL"       1)
 (setvar "DIMTOH"       0)
 (setvar "DIMTOL"       0)
 (setvar "DIMTOLJ"       1)
 (setvar "DIMTP"       0.000)
 (setvar "DIMTSZ"       0.000)
 (setvar "DIMTVP"       0.0000)
; (setvar "DIMTXSTY"       "ROMANS")
 (setvar "DIMTXT"       2.500)
 (setvar "DIMTZIN"       0)
 (setvar "DIMUNIT"       2)
 (setvar "DIMUPT"       0)
 (setvar "DIMZIN"       0)
);defun
