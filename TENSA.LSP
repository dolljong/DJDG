(DEFUN C:tensa()
    (setvar "CMDECHO" 0)
    (TEXTSCR)
;   (prompt "+--------------------+") (TERPRI)
;   (prompt "| TENSA VERSION 2.0  |") (TERPRI)
;   (prompt "|     1998,12,02     |") (TERPRI)
;   (prompt "|  DASAN ENGINEERING |") (TERPRI)
;   (prompt "|  구조부 : 김성태   |") (TERPRI)
;   (prompt "+--------------------+") (TERPRI)
   ; (COMMAND "DELAY" "1")
    (GRAPHSCR) (setq a (ssget))
    (setq gp (getpoint "\n기준이 되는 점을 찍어주세요... : "))
    (SETQ gn (GEtreal "기준이 되는 지점의 EL. <0.000M>: "))
             (if (= gn nil) (setq gn 0))
   ; (setq sp (getpoint "\nEnter Start Point : "))
    (SETQ ea (GETSTRING "그리드 형식 < 1 >: "))
             (if (= ea "") (setq ea "1"))
    (SETQ di (GETSTRING "그리드 크기 < SR-110 , SR-80 , SR-55 > 중 기본은 < 110 >: "))
             (if (= di "") (setq di "110"))
    (SETQ an (GEtreal "글씨 각도 <0>: "))
             (if (= an nil) (setq an 0))
    (setq ts(getvar "textsize"))
    (setq index 0)   (setq n (sslength a))
    (setq ls (* ts 1.6667))
   (repeat n
          (setq b1 (entget (ssname a index)))
          (setq index (1+ index))
          (setq s (assoc 10 b1 ))
          (setq e (assoc 11 b1 ))
          (setq s1(cadr s))        (setq s2(caddr s))
          (setq s1(rtos s1 2 4))   (setq s2(rtos s2 2 4))
          (setq s1(atof s1))       (setq s2(atof s2))
          (setq e1(cadr e))        (setq e2(caddr e))
          (setq e1(rtos e1 2 4))   (setq e2(rtos e2 2 4))
          (setq e1(atof e1))       (setq e2(atof e2))
          (setq l1(- s1 e1))       (setq el1(- s2 e2))
          (setq l11(abs l1))       (setq el1(abs el1))
          (setq l1 (rtos l1 2 3))

          (setq hi(- s2 (cadr gp))) (setq hi(+ (/ hi 1000) gn))
          (setq hi(rtos hi 2 3))

      (if (or (= l1 "0.000") (= el1 "0.000"))
         (sub2) (sub1)
      )
       (setq sp (list (/ (+ (cadr s) (cadr e)) 2) (+ (caddr e) 60)))

         (command "text" "j" "c" sp "" an t1 )
      (if (= an 0)
           (progn
                  (setq sp (list (car sp) (- (cadr sp) ls))))
                  (setq sp (list (+ (car sp) ls) (cadr sp)))
      )
   )
    (setvar "CMDECHO" 1)
)

(defun sub1()
    (setq l11 (/ l11 1000)) (setq fi1(rtos l11 2 3))
    (setq t1(strcat "L"ea" ""SR"DI" ""H="hi"M"" ""L="fi1"M"))
)
(defun sub2()
    (setq el1 (/ el1 1000))(setq fi1(rtos el1 2 3))
    (setq t1(strcat "L"ea" ""SR"DI "H="hi"M" "L="fi1"M"))
)
