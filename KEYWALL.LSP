(defun c:keywall()
;   (prompt "+---------------------+") (TERPRI)
;   (prompt "| keywall VERSION 2.0 |") (TERPRI)
;   (prompt "|      1998,12,02     |") (TERPRI)
;   (prompt "|  DASAN ENGINEERING  |") (TERPRI)
;   (prompt "|  구조부 : 김성태    |") (TERPRI)
;   (prompt "+---------------------+") (TERPRI)
  (setvar "cmdecho" 0)
  (setq la(getvar "clayer"))  (setq bl(getvar "blipmode"))
  ;(command "limits" "off")
  (setvar "blipmode" 0)
  (command "STYLE" "GHS" "ROMANS,GHS" "" "" "" "" "")
  (command "layer" "m" "ren" "c" "7" "" "")
  (command "layer" "m" "dim" "c" "3" "" "")
;   (prompt " 업무 하시는데 만은 도움이 되길 바람니다 .....")
  (command "vslide" "key")
;=======================================================
  (setq tensa (getstring "그리드 을 설치 하려면 <1> , 아니면 <2> :"))
    (if (= tensa "") (setq tensa "1"))
    (if (= tensa "1")
        (progn
         (setq fname (getstring "화일 이름 을입력 하세요...:"))
        )
    )
  (setq slp (getreal "보강토 옹벽 전면 Slope < 1 : 0 , 1 : 8 , 1 : 16 >중 기본은 1 : 0 :"))
    (if (= slp nil) (setq slp 0))
  (setq ty (getstring "굴착 형식 < 1 > :"))
    (if (= ty "") (setq ty "1"))
;=======================================================
  (setq h1 (getreal "좌측 굴착 깊이 < H1 > :"))
  (if (= ty "2")
      (progn (setq h2 (getreal "우측 굴착 깊이 < H2 > :"))
      )
  )
  (if (= ty "2")
      (progn (setq b1 (getreal "굴착 연장 < B1 > :"))
             (setq b1(+ b1 150))
      )
  )
;=======================================================
  (setq hh (getreal "보강토 옹벽 총 높이 :"))
;=======================================================
  (command "vslide" "key1")
  (setq sd1(getreal "상부 소단 길이 < B = 1000 mm > :"))
    (if (= sd1 nil) (setq sd1 1000))
  (setq sd2(getreal "비탈면 기울기 < 1 : L'=2 > :"))
   (if (= sd2 nil) (setq sd2 2))
   (if (/= sd2 0)
      (progn
         (setq sd3(getreal "기울기 길이 < L > :"))
      )
   )
;=======================================================
  (command "redraw")
  (setq st (getpoint "그림 그리는 위치을 찍어 주세요..:"))
  (setq st1 st)
;=======================================================
  (command "layer" "s" "dim" "")
  ;(setq n(/ hh 200))
   (setq nn 0)
       (if (= slp 0)
           (progn (key1))
       )
       (if (= slp 8)
           (progn (key3))
       )
       (if (= slp 16)
           (progn (key2))
        )
  (if (= tensa "1")
     (progn
          (sub1)
     )
  )
  (setq in1 "0")
  (if (= tensa "1")
    (progn
       (while (/= in1 "9")
          (setq inlina (read-line tfile))
;         (setq inline (read-line tfile))
          (sub2)
;         (command "text" st_1 "" "" in1)
;         (command "text" st_2 "" "" in2)
       )
    )
  )
    (exc)
; (if (= tensa "1")
;    (progn
        (sub3)
;    )
; )
    (dim)
)
;================================================
 (defun key1()
   (command "insert" "*stone" st "" "")
   (while (/= hh nn)
            (keb1)
            (setq st(list (car st) (+ (cadr st) 200)))
            (setq nn (+ nn 200))
   )
   (ket1)
 )
;================================================
 (defun key2()
   (command "insert" "*stone" st "" "")
   (setq mm 0)
   (while (/= hh nn)
            (if (= mm 2)
              (progn
               ; (setq st(list (+ (car st) 25) (+ (cadr st) 200)))
                 (setq st(list (+ (car st) 25) (cadr st)))
              (setq mm 0)
              )
            )
            (keb1)
                (setq st(list (car st) (+ (cadr st) 200)))
                (setq mm (+ mm 1))
                (setq nn (+ nn 200))
   )
   (ket1)
 )
;================================================
 (defun key3()
   (command "insert" "*stone" st "" "")
   (while (/= hh nn)
            (keb1)
            (setq st(list (+ (car st) 25) (+ (cadr st) 200)))
            (setq nn (+ nn 200))
   )
   (ket1)
 )
;================================================
 (defun keb1()
  (command "layer" "s" "ren" "")
   (setq kb1(list (+ (car st) 550) (cadr st)))
   (setq kb2(list (car kb1) (+ (cadr kb1) 200)))
   (setq kb3(list (- (car kb2) 550) (cadr kb2)))
    (command "pline" st kb1 kb2 kb3 "c")
 )
;================================================
 (defun ket1()
  (command "layer" "s" "ren" "")
   (setq kt1(list (+ (car st) 275) (cadr st)))
   (setq kt2(list (car kt1) (+ (cadr kt1) 100)))
   (setq kt3(list (- (car kt2) 275) (cadr kt2)))
    (command "pline" st kt1 kt2 kt3 "c")
 )
;================================================
 (defun exc()
  (command "layer" "s" "ren" "")
   (setq ex1(list (- (car st1) 150) (- (cadr st1) 150)))
   (setq ex2(list (- (car ex1) h1) (+ (cadr ex1) h1)))
   (setq ex3(list (+ (car ex1) 850) (cadr ex1)))
   (if (= ty "1")
       (progn
         (setq ex4(list (+ (car ex3) h1) (+ (cadr ex3) h1)))
       )
   )
    (command "line" ex1 ex2 "")
         (setq ex6(list (- (car ex2) 1000) (cadr ex2)))
    (if (= ty "1")
       (progn
         (setq ex7(list (+ (car ex4) 1000) (cadr ex4)))
         (command "line" ex3 ex4 "")
         (command "line" ex2 ex6 "")
         (command "line" ex4 ex7 "")
         (command "layer" "s" "dim" "")
         (command "line" ex2 ex4 "")
         (command "layer" "s" "ren" "")
         )
    )

     (if (= ty "2")
         (progn
            (setq h3(- h1 h2))
            (setq b2(- b1 850))
            (setq ex4(list (+ (car ex3) h3) (+ (cadr ex3) h3)))
            (setq ex5(list (+ (car ex4) b2) (cadr ex4)))
         )
     )
;================================================================
         (setq es 0) (setq eh 0)
  ; (if (/= slp 0)
  ;        (progn
  ;          (setq es(/ 1 slp)) (setq eh(* es h2))
  ;        )
  ;  )
    (if (= ty "2")
           (progn
        (if (/= slp 0)
           (progn
             (setq es(/ 1 slp)) (setq eh(* es h2))
           )
        )
             (setq ex8(list (+ (car ex5) eh) (+ (cadr ex5) h2)))
             (setq ex9(list (+ (car ex8) 1000) (cadr ex8)))
             (command "line" ex3 ex4 ex5 "")
             (command "line" ex5 ex8 ex9 "")
             (command "line" ex2 ex6 "")
             (command "layer" "s" "dim" "")
             (command "line" ex2 ex8 "")
           )
     )
     (command "layer" "s" "ren" "")
 )
;================================================
 (defun sub1()
     (setq tfile (open fname "r")
       inline (read-line tfile)
   )
 )
;================================================
 (defun sub2()
       (setq in1(substr inlina 1 1)  in2(substr inlina  5 6)
             in3(substr inlina 14 6)  in4(substr inlina 34 7)
         )
       (setq ht_1(* (atof in2) 1000))  (setq le_1(* (atof in3) 1000))
       ;(setq re_1(atof in4))
   (command "layer" "s" "0" "")
       (if (= slp 0)
         (progn (setq st_1(list (car st1) (+ (cadr st1) ht_1)))
                (setq st_2(list (+ (car st_1) le_1) (cadr st_1)))
         )
       )

       (if (= slp 8)
         (progn (setq slp_1 0.125)
             ;  (setq slp_2(abs (- ht_1 (cadr st1))))
                (setq slp_3(* ht_1 slp_1))
                (setq st_1(list (+ (car st1) slp_3) (+ (cadr st1) ht_1)))
                (setq st_2(list (+ (car st_1) le_1) (cadr st_1)))
         )
       )

       (if (= slp 16)
         (progn (setq slp_4 0.0625)
             ;  (setq slp_5(abs (- ht_1 (cadr st1))))
                (setq slp_6(* ht_1 slp_4))
                (setq st_1(list (+ (car st1) slp_6) (+ (cadr st1) ht_1)))
                (setq st_2(list (+ (car st_1) le_1) (cadr st_1)))
         )
       )
    (command "line" st_1 st_2 "")
 )
;================================================
 (defun sub3()
     (command "layer" "m" "cenc" "c" "1" "" "")
     (command "layer" "s" "cenc" "")
  (setq id1(list (+ (car kt3) sd1) (cadr kt3)))
  (if (/= sd2 0)
     (progn
         (setq sd21(/ 1 sd2))
         (setq sd31(* sd21 sd3))
         (setq id2(list (+ (car id1) sd3) (+ (cadr id1) sd31)))
         (command "line" kt3 id1 id2 "")
     )
  )
  (if (= sd2 0)
     (progn
         (setq id2(list (+ (car id1) 5000) (cadr id1)))
         (command "line" kt3 id2 "")
     )
  )
 )
;================================================
 (defun dim()
      (setq dim_1(list (- (car ex2) 500) (cadr ex2)))
      (setq dim_2(list (+ (car dim_1) 700) (+ (cadr dim_1) (- hh (- h1 250)))))
         (command "layer" "s" "dim" "")
         (command "dim" "vert" dim_1 dim_2 dim_1 "" "e")
 )
