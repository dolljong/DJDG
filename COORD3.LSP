;*********************************************
; Program : COORD3
;           Coord Marking
;           Yi Suk-Jong
;           03/02/13
;*********************************************
; 좌표값을 도면에 표시(측량좌표계로 변환-X,Y바꿈)
; x=12.345
; y=24.456
;*********************************************
(defun c:coord3()

  (defun SETERR(s)
    (if (/= s "Function cancelled")
        (princ (strcat "\nError: " s))
    ); of If
    (setq *error* oer seterr nil)
    (princ)
  ); of SETERR
  (setq oer *error* *error* seterr)

  (setq ts (* (getvar "DIMTXT") (GETVAR "DIMSCALE")))       ;dimension text크기

  (setq pt1 (getpoint "Pick First Point:"))
  (setq pt2 (getpoint pt1 "Pick Second Point:"))
  (setq px (car pt1))
  (setq py (cadr pt1))
  ;****** real to string
  (setq pxt (strcat "X=" (rtos py 2 (getvar "luprec"))))    ;y좌표를 x좌표값(측량)
  (setq pyt (strcat "Y=" (rtos px 2 (getvar "luprec"))))    ;x좌표를 y좌표값(측량)
  (command "dim1" "leader" pt1 pt2 "" pxt)
  (setq txtpnt (cdr (assoc 10 (entget (entlast)))))         ;text삽입점
  (setq txtpnt1 (list (car txtpnt)
                      (- (cadr txtpnt) (* 1.5 ts)) 0.0))            ;y좌표 삽입점
  (if (< (car pt2) (car pt1)) 
    (setq algn "MR")
    (setq algn "ML")
  )
  (command "TEXT" algn txtpnt1 ts "0.0" pyt)                ;y좌표값 쓰기

  (setq *error* oer seterr nil)
  (princ)

);;; End of program COORD
